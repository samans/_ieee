module ieee802-dot1as-ftt {
  yang-version 1.1;
  namespace "urn:ieee:std:802.1AS:yang:ieee802-dot1as-ftt";
  prefix dot1as-ftt;

  import ieee1588-ptp-tt {
    prefix ptp-tt;
  }

  organization
    "IEEE 802.1 Working Group";
  contact
    "WG-URL: http://www.ieee802.org/1/
     WG-EMail: stds-802-1-L@ieee.org
     Contact: IEEE 802.1 Working Group Chair
     Postal: C/O IEEE 802.1 Working Group
     IEEE Standards Association
     445 Hoes Lane
     Piscataway, NJ 08854
     USA
     E-mail: stds-802-1-chairs@ieee.org";
  description
    "Management objects that control fault-tolerant timing with time
     integrity (FTT) entities as specified in IEEE Std 802.1ASed-2025.

     References in this YANG module are to IEEE Std 802.1AS-2025
     as amended by IEEE Std 802.1ASed-2025.

     Copyright (C) IEEE (2025).
     This version of this YANG module is part of IEEE Std 802.1AS;
     see the standard itself for full legal notices.";

  revision 2025-10-08 {
    description
      "Published as part of IEEE Std 802.1ASed-2025.
       Initial version.";
    reference
      "IEEE Std 802.1AS - Timing and Synchronization for Time-Sensitive
      Applications: IEEE Std 802.1AS-2025, IEEE Std 802.1ASed-2025.";
  }

  feature ftt {
    description
      "This feature indicates that the device supports the FTT service.";
  }

  typedef ftt-output-trust-state-type {
    type enumeration {
      enum NOT-TRUSTED {
        value 0;
        description
          "Integrity of time synchronization function is not acheived";
      }
      enum TIME-TRUSTED {
        value 1;
        description
          "Integrity of time synchronization is achieved";
      }
      enum FREQ-TRUSTED {
        value 2;
        description
          "Only the integrity of the rate-of-change of time is achieved.";
      }
      enum INIT {
        value 3;
        description
          "System is waiting to be invoked and has not determined a trust
           state.";
      }
    }
    description
      "The fttOutputTrustState type is an enumerated value that holds
       the trust state of the FTT entity.";
    reference
      "20.3.2.1 of IEEE Std 802.1AS.";
  }
  
  typedef ftt-input-trust-state-type {
    type enumeration {
      enum INACTIVE {
        value 0;
        description
          "The FTT input is not considered to be providing time values.";
      }
      enum ACTIVE {
        value 1;
        description
          "The FTT input is actively providing time values.";
      }
      enum TRUSTED {
        value 2;
        description
          "The FTT input is actively providing trusted time values.";
      }
      enum UNTRUSTED {
        value 3;
        description
          "The FTT input is actively providing untrusted time values.";
      }
    }
    description
      "The fttInputTrustState type is an enumerated value that holds
       the trust state of an FTT input.";
    reference
      "20.3.2.2 of IEEE Std 802.1AS.";
  }
         

  typedef uint48 {
    type uint64 {
      range "0..281474976710655";
    }
    description
      "Unsigned 48-bit integer.";
  }

  grouping fault-tolerant-timing-group {
    description
      "Management of a single FTT entity.";
    reference
      "14.23 of IEEE Std 802.1AS";
    leaf ftt-max-inputs {
      type uint8 {
        range "0..16";
      }
      config false;
      description
        "Maximum number of input ClockTarget Interfaces available on the
         FTT entity.";
      reference
        "14.23.2 of IEEE Std 802.1AS.";
    }
    leaf ftt-num-inputs {
      type uint8;
      description
        "The number of input ClockTarget Interfaces currently enabled on the
         FTT entity.";
      reference
        "14.23.3 of IEEE Std 802.1AS.";
    }
    leaf ftt-max-dtsfs {
      type uint8 {
        range "0..126";
      }
      config false;
      description
        "Maximum number of DTSF instances available in the FTT entity.";
      reference
        "14.23.4 of IEEE Std 802.1AS.";
    }
    leaf ftt-num-dtsfs {
      type uint8;
      description
        "Number of DTSF instances enabled in the FTT entity.";
      reference
        "14.23.5 of IEEE Std 802.1AS.";
    }
    leaf ftt-dtsf-max-inputs {
      type uint8 {
        range "0..16";
      }
      config false;
      description
        "Maximum number of input ClockTarget Interfaces available on each DTSF
         instance in the FTT entity.";
      reference
        "14.23.6 of IEEE Std 802.1AS.";
    }
    list ftt-inputs-to-tsf {
      key "tsf-instance-number";
      description
        "Mapping of FTT entity input ClockTarget Interface index numbers to TSF
         instance numbers.";
      reference
        "14.23.7 of IEEE Std 802.1AS.";
      leaf tsf-instance-number {
        type uint8;
        description
          "The TSF instance number that the FTT entity's input index number is
           connected to.";
        reference
          "20.2.3 of IEEE Std 802.1AS.";
      }
      leaf assigned-inputs {
        type uint16;
        description
          "The bit map of FTT inputs that are assigned to the TSF instance.
           The most-significant bit corresponds to input index 16, the least-
           significant bit corresponds to input index 1. The number of inputs
           assigned to any DTSF instance (i.e., TSF instance with tsf-instance-number of 1 or higher) cannot be greater than fttDtsfMaxInputs.";
        reference
          "14.23.7 of IEEE Std 802.1AS.";
      }
    }
    list ftt-ptp-instance-to-input {
      key "ftt-input-index";
      description
        "Mapping of PTP Instance index numbers to FTT entity input index
         numbers.";
      reference
        "14.23.8 of IEEE Std 802.1AS.";
      leaf ftt-input-index {
        type uint8;
        description
          "The FTT entity's input index number.";
        reference
          "20.2.1 of IEEE Std 802.1AS.";
      }
      leaf ptp-instance-index {
        type uint32;
        description
          "The instanceIndex number of the PTP Instance that is connected to
           the FTT input.";
        reference
          "14.1.1 of IEEE Std 802.1AS-2020.";
      }
    }
    list ftt-hyst {
      key "ftt-input-index";
      description
        "Hysteresis values to be added to fttMaxAs for pairs of input
         ClockTarget interfaces.";
      reference
        "14.23.9 of IEEE Std 802.1AS.";
      leaf ftt-input-index {
        type uint8;
        description
          "The first input index number.";
        reference
          "20.2.1 of IEEE Std 802.1AS.";
      }
      list hyst-list {
        key "ftt-input-index";
        description
          "Hysteresis values for pairs of input ClockTarget interfaces.";
        reference
          "14.23.9 of IEEE Std 802.1AS.";
        leaf ftt-input-index {
          type uint8;
          description
            "The second input index number.";
          reference
            "20.2.1 of IEEE Std 802.1AS.";
        }
        leaf hyst-value {
          type ptp-tt:time-interval;
          default "0";
          description
            "Hysteresis value to be added to fttMaxAs for the pair of input
             interfaces.";
          reference
            "14.23.9 of IEEE Std 802.1AS.";
        }
      }
    }
    list ftt-max-as {
      key "ftt-input-index";
      description
        "Maximum expected skew between pairs of input ClockTarget interfaces.";
      reference
        "14.23.10 of IEEE Std 802.1AS.";
      leaf ftt-input-index {
        type uint8;
        description
          "The first input index number.";
        reference
          "20.2.1 of IEEE Std 802.1AS.";
      }
      list max-as-list {
        key "ftt-input-index";
        description
          "The second input index number.";
        reference
          "14.23.10 of IEEE Std 802.1AS.";
        leaf ftt-input-index {
          type uint8;
          description
            "The second input index number.";
          reference
            "20.2.1 of IEEE Std 802.1AS.";
        }
        leaf max-as-value {
          type ptp-tt:time-interval;
          default "0";
          description
            "Maximum expected skew between the pair of input interfaces when
             those time values are not faulty.";
          reference
            "14.23.10 of IEEE Std 802.1AS.";
        }
      }
    }
    list ftt-sel-change-thresh {
      key "tsf-instance-number";
      description
        "Time difference change threshold used by TSF instances.";
      reference
        "14.23.11 of IEEE Std 802.1AS.";
      leaf tsf-instance-number {
        type uint8;
        description
          "The TSF instance number.";
        reference
          "20.2.3 of IEEE Std 802.1AS.";
      }
      leaf change-threshold {
        type ptp-tt:time-interval;
        description
          "the TimeInterval threshold used by the TSF instance.";
        reference
          "14.23.11 of IEEE Std 802.1AS.";
      }
    }
    leaf ftt-rr-thresh {
      type uint32;
      default "0";
      description
        "Maximum rate-ratio offset magnitude deemed acceptable for FREQ_TRUSTED
         state.";
      reference
        "14.23.12 of IEEE Std 802.1AS.";
    }
    leaf ftt-rr-thresh-std-dev {
      type uint32;
      default "0";
      description
        "Maximum standard deviation of rate-ratio offset deemed acceptable for 
         FREQ_TRUSTED state.";
      reference
        "14.23.13 of IEEE Std 802.1AS.";
    }
    list ftt-use-nq {
      key "tsf-instance-number";
      description
        "Specifies whether a TSF instance uses the NQ input when no trusted
         time is available.
         If ftt-use-nq is TRUE, the use of the NQ input is enabled.
         If ftt-use-nq is FALSE, the use of the NQ input is not enabled.
         The default value is implementation-specific";
      reference
        "14.23.14 and 20.2.4 of IEEE Std 802.1AS.";
      leaf tsf-instance-number {
        type uint8;
        description
          "The TSF instance number.";
        reference
          "20.2.3 of IEEE Std 802.1AS.";
      }
      leaf use-nq {
        type boolean;
        description
          "whether the TSF instance uses the NQ input.";
        reference
          "14.23.14 of IEEE Std 802.1AS.";
      }
    }
    leaf ftt-use-ftt-clk {
      type boolean;
      description
        "Defines whether the FTT_CLK frequency is used as a reference for time
         integrity.
         If fttUseFTTClk is TRUE, the FTT_CLK frequency is used as a reference
         for checking time integrity. 
         If fttUseFTTClk is FALSE, the FTT_CLK frequency is not used as a
         reference for checking time integrity.
         The default value is implementation-specific.";
      reference
        "14.23.15 of IEEE Std 802.1AS.";
    }
    list ftt-tsf-sel-input {
      key "tsf-instance-number";
      config false;
      description
        "The index number of the FTT input selected by each TSF instance.";
      reference
        "14.23.16 and 20.3.2.3 of IEEE Std 802.1AS.";
      leaf tsf-instance-number {
        type uint8;
        description
          "The TSF instance number.";
        reference
          "20.2.3 of IEEE Std 802.1AS.";
      }
      leaf selected-ftt-input-index {
        type uint8;
        description
          "FTT input index that is selected by the TSF instance.";
        reference
          "14.23.16 of IEEE Std 802.1AS.";
      }
    }
    leaf ftt-sel-instance {
      type uint32;
      config false;
      description
        "Instance index of the PTP Instance selected as the trusted time
         source.";
      reference
        "14.23.17 of IEEE Std 802.1AS.";
    }
    list ftt-tsf-sel-change-cnt {
      key "tsf-instance-number";
      config false;
      description
        "The number of times each TSF has changed its selection.";
      reference
        "14.23.18 of IEEE Std 802.1AS.";
      leaf tsf-instance-number {
        type uint8;
        description
          "The TSF instance number.";
        reference
          "20.2.3 of IEEE Std 802.1AS.";
      }
      leaf sel-change-cnt {
        type uint16;
        description
          "The number of times the TSF instance has changed its selection.";
        reference
          "14.23.18 of IEEE Std 802.1AS.";
      }
    }
    list ftt-input-trust-state {
      key "ftt-input-index";
      config false;
      description
        "Trust state of all FTT inputs.";
      reference
        "14.23.19 of IEEE Std 802.1AS.";
      leaf ftt-input-index {
        type uint8;
        description
         "The FTT input index.";
        reference
          "14.23.16 of IEEE Std 802.1AS.";
      }
      leaf ftt-input-trust-state {
        type ftt-input-trust-state-type;
        description
          "Trust state of the FTT input.";
        reference
          "14.23.19 of IEEE Std 802.1AS.";
      }
    }
    leaf ftt-trust-state {
      type ftt-output-trust-state-type;
      default "NOT-TRUSTED";
      config false;
      description
        "The trust state of the FTT entity.";
      reference
        "14.23.20 and 20.3.2.1 of IEEE Std 802.1AS.";
    }
    leaf ftt-state-change-cnt {
      type uint16;
      default "0";
      config false;
      description
        "Number of times the FTT entity has changed its trust state.";
      reference
        "14.23.21 of IEEE Std 802.1AS.";
    }
  }

  augment "/ptp-tt:ptp/ptp-tt:common-services" {
    description
      "Augment IEEE Std 1588 commonServices with ftt-service.";
    container ftt-service {
      if-feature "ftt";
      description
        "The FTT service structure contains the fttSystemList, which is a list
         of instances of the FTT service.";
      reference
        "14.23 of IEEE Std 802.1AS";
      list ftt-system {
        key "ftt-system-index";
        description
          "Indexed list of FTT entity systems in the FTT service";
        leaf ftt-system-index {
          type uint8;
          description
            "Index for the FTT entity system.";
        }
        container ftt-system-ds {
          description
            "The fttSystemDS describes the attributes of the
             respective instance of the FTT service.";
          reference
            "14.23 of IEEE Std 802.1AS";
          uses fault-tolerant-timing-group;
        }
        container ftt-system-description-ds {
          description
            "The fttSystemDescriptionDS contains descriptive information for the
             respective instance of the FTT service.";
          reference
            "14.24 Fault-Tolerant Timing System Description Parameter
             Data Set (fttSystemDescriptionDS) of IEEE Std 802.1AS";
          leaf user-description {
            type string {
              length "0..128";
            }
            description
              "Configuration description of the Fault-Tolerant Timing system.";
            reference
              "14.24.2 of IEEE Std 802.1AS";
          }
        }
      }
    }
  }
}
