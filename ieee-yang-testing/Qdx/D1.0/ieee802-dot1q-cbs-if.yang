module ieee802-dot1q-cbs-if {

  namespace urn:ieee:std:802.1Q:yang:ieee802-dot1q-cbs-if;
  prefix cbs-if;
  
  import ietf-interfaces {
    prefix if;
  }
  import ieee802-dot1q-cbs {
    prefix cbs;
  }
  
  organization
    "IEEE 802.1 Working Group";
  contact
  	"WG-URL: http://www.ieee802.org/1/
  	WG-EMail: stds-802-1-L@ieee.org

  	Contact: IEEE 802.1 Working Group Chair
  	Postal: C/O IEEE 802.1 Working Group
  	IEEE Standards Association
  	445 Hoes Lane
  	P.O. Box 1331
  	Piscataway
  	NJ 08855-1331
   	USA

   	E-mail: STDS-802-1-L@IEEE.ORG";
  
  description 
    "This module provides for management of IEEE Std 802.1Q bridges
     that support the Credit Based Shaper
    
    Copyright (C) IEEE (2023).";

  revision 2023-10-12
  {
	description
      "Published as part of IEEE Std 802.1Qdx
       Initial version.";
    reference
      "IEEE Std 802.1Qdx-2023, YANG Data Models for the Credit-Based Shaper.";
  }
  feature credit-based-shaper {
    description
      "Credit Based Shaper supported.";
    reference
      "8.6.8.2 of IEEE Std 802.1Q";
  }
  augment "/if:interfaces/if:interface" {
    if-feature "credit-based-shaper";
    description
      "Augment interface with Credit Based Shaper configuration.";
    uses cbs:cbs-config;
  }
}
