module ieee802-dot1cb-autoconf {
  yang-version "1.1";
  namespace urn:ieee:std:802.1Q:yang:ieee802-dot1cb-autoconf;
  prefix dot1cb-autoconf;
  
  import ieee802-dot1q-types {
    prefix dot1qtypes;
  }
  import ieee802-dot1cb-frer {
    prefix dot1cb-frer;
  }
  import ieee802-dot1cb-stream-identification {
    prefix dot1cb-sid;
  }
  import ietf-interfaces {
    prefix if;
  }

  organization
    "Institute of Electrical and Electronics Engineers";
  contact
    "WG-URL: http://ieee802.org/1/
    WG-EMail: stds-802-1-l@ieee.org
    
    Contact: IEEE 802.1 Working Group Chair
    Postal: C/O IEEE 802.1 Working Group
            IEEE Standards Association
            445 Hoes Lane
            Piscataway, NJ 08854
            USA
    
    E-mail: stds-802-1-chairs@ieee.org";
  description
    "Management objects that support the automatic configuration, upon receipt
	of a packet, of entries in the following tables: Stream identity table, 
	Sequence generation table, Sequence recovery table and Sequence
	identification table. They are described in Clause E.x.x of
	IEEE Std 802.1CB-2027.";

  revision 2026-08-18 {
    description
      "Published as part of IEEE Std 802.1CB-2027, Frame Replication and
	  Elimination for Reliability. FRER autoconfiguration YANG model.";
    reference
      "Annex E of IEEE Std 802.1CB-2027.";
  }

  feature auto-configuration {
    description
      "Autoconfiguration of entries in the tables for Stream identity
      table, sequence recovery table, and sequence identification table.";
    reference
      "Annex E of IEEE Std 802.1CB-2027";
  }

  augment "/dot1cb-frer:frer" {
    description
      "Add a description here";
    container autoconfiguration {
      if-feature "auto-configuration";
      description
        "Container for Autoconfiguration managed objects.";
      reference
        "Annex E of IEEE Std 802.1CB-2027";
      list sequence {
        key "index";
        description
          "There is one Sequence autoconfiguration table per system. It
          contains any number of table entries. No two (or more) entries
          in the Sequence autoconfiguration table can have the same
          values for frerAutSeqSeqEncaps, frerAutSeqTagged, and
          frerAutSeqVlan on any given port. Each frerAutSeqEntry object
          relates to a single class of Streams, and specifies how entries
          are created (and destroyed) in the Stream identity table, the
          Sequence recovery table, and the Sequence identification table.";
        reference
          "E.3.2.1 of IEEE Std 802.1CB-2027";
        leaf index {
          type uint32;
          description
            "Entry in the sequence list referencing to a single class of
            Streams.";
        }
        container sequence-encapsulation {
          description
            "An enumerated value, specifying which Sequence encode/decode
            function, and therefore, which type sequence_number encoding,
            is to be recognized for the purposes of Autoconfiguration.";
          reference
            "E.3.2.1.1.1 of IEEE Std 802.1CB-2027";
          uses dot1cb-frer:sequence-encode-decode;
        }
        leaf-list receive-port {
          type if:interface-ref;
          min-elements 1;
          description
            "The list of ports to which this frerAutSeqEntry applies, and
            on which Stream identification functions, Sequence
            encode/decode functions, and Individual recovery functions
            are to be autocreated.";
          reference
            "E.3.2.1.1.2 of IEEE Std 802.1CB-2027";
        }
        leaf tagged {
          type enumeration {
            enum tagged {
              value 1;
              description
                "A frame must have a VLAN tag to be matched.";
            }
            enum priority {
              value 2;
              description
                "A frame must be untagged, or have a VLAN tag with a VLAN
                ID = 0 to be matched.";
            }
            enum all {
              value 3;
              description
                "A frame is matched whether tagged or not.";
            }
          }
          description
            "An enumerated value indicating whether packets to be matched
            by this frerAutSeqEntry are permitted to have a VLAN tag.";
          reference
            "E.3.2.1.1.3 of IEEE Std 802.1CB-2027";
        }
        leaf-list vlan {
          type dot1qtypes:vlanid;
          description
            "A list of vlan_identifiers for the packet to match. A null
            list matches all vlan_identifiers.";
          reference
            "E.3.2.1.1.4 of IEEE Std 802.1CB-2027";
        }
        leaf-list recovery-port {
          type if:interface-ref;
          min-elements 1;
          description
            "The list of ports on which Sequence recovery functions are
            to be autocreated by this frerAutSeqEntry.";
          reference
            "E.3.2.1.1.5 of IEEE Std 802.1CB-2027";
        }
        leaf destruction-interval {
          type uint64;
          units "ms";
          default "86400000";
          description
            "An integer number of milliseconds after which an idle set of
            functions created by this frerAutSeqEntry can be destroyed. A
            value of 0 indicates that idle autoconfigured functions are
            not to be destroyed. Default value is 86 400 000 decimal (one
            day).";
          reference
            "E.3.2.1.1.6 of IEEE Std 802.1CB-2027";
        }
        leaf reset-interval {
          type uint64;
          units "ms";
          description
            "The value used to fill frerSeqRcvyResetMSec when
            autoconfiguring entries in the Sequence recovery table.";
          reference
            "E.3.2.1.1.7 of IEEE Std 802.1CB-2027";
        }
        container algorithm {
          description
            "The value used to fill frerSeqRcvyAlgorithm when
            autoconfiguring entries in the Sequence recovery table.";
          reference
            "E.3.2.1.1.8 of IEEE Std 802.1CB-2027";
          uses dot1cb-frer:sequence-recovery-algorithm;
        }
        leaf history-length {
          type dot1cb-frer:sequence-history-length;
          default "2";
          description
            "The value used to fill frerSeqRcvyHistoryLength when
            autoconfiguring entries in the Sequence recovery table.";
          reference
            "E.3.2.1.1.9 of IEEE Std 802.1CB-2027";
        }
        leaf create-individual {
          type boolean;
          description
            "A Boolean value. If True, the receipt of a packet that
            triggers the autoconfiguration of a new tsnStreamIdEntry also
            triggers the instantiation of a frerSeqRcvyEntry for an
            Individual recovery function.";
          reference
            "E.3.2.1.1.10 of IEEE Std 802.1CB-2027";
        }
        leaf create-recovery {
          type boolean;
          description
            "A Boolean value. If True, the receipt of a packet that
            triggers the autoconfiguration of a new tsnStreamIdEntry can
            also trigger the instantiation of a frerSeqRcvyEntry for a
            Sequence recovery function.";
          reference
            "E.3.2.1.1.11 of IEEE Std 802.1CB-2027";
        }
        leaf latent-error-detection {
          type boolean;
          description
            "A Boolean value. If True, the autoconfiguration of a new
            Sequence recovery function also creates an associated Latent
            Error Detection function.";
          reference
            "E.3.2.1.1.12 of IEEE Std 802.1CB-2027";
        }
        leaf latent-error-difference {
          type int32;
          description
            "The value used to fill frerSeqRcvyLatentErrorDifference when
            autoconfiguring entries in the Sequence recovery table.";
          reference
            "E.3.2.1.1.13 of IEEE Std 802.1CB-2027";
        }
        leaf latent-error-period {
          type uint32;
          units "ms";
          default "2000";
          description
            "The value used to fill frerSeqRcvyLatentErrorPeriod when
            autoconfiguring entries in the Sequence recovery table.";
          reference
            "E.3.2.1.1.14 of IEEE Std 802.1CB-2027";
        }
        leaf latent-error-reset-period {
          type uint32;
          units "ms";
          default "30000";
          description
            "The value used to fill frerSeqRcvyLatentResetPeriod when
            autoconfiguring entries in the Sequence recovery table.";
          reference
            "E.3.2.1.1.15 of IEEE Std 802.1CB-2027";
        }
      }
      list output {
        key "index";
        description
          "There is one Output autoconfiguration table per system. It
          contains any number of frerAutOutEntry objects, each relating
          to a single class of Streams specifying how active entries are
          created in the Sequence identification table. No two (or more)
          entries in the Output autoconfiguration table can include the
          same port in their frerAutSeqReceivePortList objects.";
        reference
          "E.3.2.2 of IEEE Std 802.1CB-2027";
        leaf index {
          type uint32;
          description
            "Entry in the output list referencing to a single class of
            Streams.";
        }
        leaf-list port {
          type if:interface-ref;
          min-elements 1;
          description
            "The list of ports to which this frerAutOutEntry applies, and
            on which active Sequence encode/decode functions are to be
            autocreated.";
          reference
            "E.3.2.2.1.1 of IEEE Std 802.1CB-2027";
        }
        container encapsulation {
          description
            "An enumerated value, specifying which Sequence encode/decode
            function, and therefore, which type sequence_number encoding,
            is to be used for autoconfigured Streams on the ports in
            frerAutSeqReceivePortList.";
          reference
            "E.3.2.2.1.2 of IEEE Std 802.1CB-2027";
          uses dot1cb-frer:sequence-encode-decode;
        }
        leaf lan-path-id {
          type dot1cb-frer:lan-path-id;
          description
            "An integer specifying a path or LAN. If and only if
            frerAutOutEncaps specifies HSR or PRP frerAutOutLanPathId
            specifies the LanId or PathId value to be inserted into the
            HSR sequence tag or PRP sequence trailer of autoconfigured
            packets transmitted on the ports in
            frerAutSeqReceivePortList.";
          reference
            "E.3.2.2.1.3 of IEEE Std 802.1CB-2027";
        }
      }
    }
  }
  augment "/dot1cb-sid:stream-identity" {
    if-feature "auto-configuration";
    description
      "Two managed objects augment each tsnStreamIdEntry in the Stream
      identity table when Managed objects for autoconfiguration is
      implemented.";
    reference
      "E.3.1 of IEEE Std 802.1CB-2027";
    leaf auto-configured {
      type boolean;
      config false;
      description
        "A read-only Boolean value, supplied by the system, specifying
        whether this entry was created explicitly (False) or via the
        Sequence autoconfiguration table.";
      reference
        "E.3.1.1 of IEEE Std 802.1CB-2027";
    }
    leaf lan-path-id {
      type dot1cb-frer:lan-path-id;
      description
        "An integer specifying a path or LAN. If and only if a packet
        matches an entry in the Sequence identification table that
        specifies HSR or PRP in its frerSeqEncEncapsType object,
        tsnStreamIdLanPathId specifies the LanId or PathId value that
        must be matched for this tsnStreamIdEntry to apply. A value of –1
        indicates that the LanId or PathId are to be ignored.";
      reference
        "E.3.1.2 of IEEE Std 802.1CB-2027";
    }
  }
 }
