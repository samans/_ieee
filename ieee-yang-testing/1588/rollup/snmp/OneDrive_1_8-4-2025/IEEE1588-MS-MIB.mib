IEEE1588-MS-MIB DEFINITIONS ::= BEGIN
IMPORTS
    MODULE-IDENTITY, OBJECT-IDENTITY,
    OBJECT-TYPE, Unsigned32,
    Integer32, Counter32             FROM SNMPv2-SMI         --[RFC2578]
    TEXTUAL-CONVENTION, TruthValue,
    RowStatus, TimeStamp,
    PhysAddress                      FROM SNMPv2-TC          --[RFC2579]
    OBJECT-GROUP, MODULE-COMPLIANCE  FROM SNMPv2-CONF        --[RFC2580]
    SnmpAdminString                  FROM SNMP-FRAMEWORK-MIB --[RFC3411]
    InterfaceIndexOrZero             FROM IF-MIB;            --[RFC2863]
ieee1588    MODULE-IDENTITY
    LAST-UPDATED    "202308141919Z"
    ORGANIZATION    "IEEE Working Group"
    CONTACT-INFO    "Web: https://sagroups.ieee.org/1588/
                    E-mail: 1588officers@listserv.ieee.org

                    Postal: C/O IEEE 1588 Working Group Chair
                    IEEE Standards Association
                    445 Hoes Lane
                    Piscataway, NJ 08854
                    USA"
    DESCRIPTION
        "The Management Information Base module for IEEE 1588 Std-2019,
        Precision Time Protocol version 2.1.
        The IEEE Std 1588 defines a protocol enabling precise
        synchronization of clocks in measurement and control systems
        implemented with packet-based networks, the Precision Time
        Protocol. The protocol enables heterogeneous systems that
        include clocks of various inherent precision, resolution, and
        stability to synchronize to a grandmaster clock."
    REVISION        "202308141919Z" -- 2023-08-14 : 19:19:51
    DESCRIPTION
        "This IEEE1588 MIB module allows accessing all the data made
        available to management by the IEEE Std 1588-2019 (PTPv2.1),
        including optional features. This IEEE1588 MIB is intended for
        use with the Default PTP Profiles described in the IEEE Std
        1588-2019. This IEEE1588 MIB is compatible with the Default PTP
        Profiles defined in the IEEE Std 1588-2008 (PTPv2). It is
        envisioned that this IEEE1588 MIB module is complemented with
        (extended by) MIBs specific to PTP Profiles other than the
        Default PTP Profiles. These complementary MIBs are meant to
        cover only management information specific to such PTP Profiles.
        The information data model (i.e. data sets) is defined by IEEE
        Std 1588-2019 in clause 8. The details of mapping these data
        sets into Management Information Base (MIB) are specified in
        clause 15.3 of IEEE Std 1588-2019 and this IEEE1588 MIB.
        
        This IEEE1588 MIB structure follows the structure of data sets
        defined in clause 8 (see 8.1.4.2):
        a) instanceList[]
            1)  defaultDS
            2)  currentDS
            3)  parentDS
            4)  timePropertiesDS
            5)  descriptionDS
            6)  faultLogDS
            7)  nonVolatileStorageDS
            8)  pathTraceDS
            9)  alternateTimescaleOffsetsDS
            10) holdoverUpgradeDS
            11) grandmasterClusterDS
            12) acceptableMasterTableDS
            13) performanceMonitoringDS
            14) enhancedSynchronizationAccuracyMetricsDS
            15) portList[]
                i)    portDS
                ii)   timestampCorrectionPortDS
                iii)  asymmetryCorrectionPortDS
                iv)   descriptionPortDS
                v)    unicastNegotiationPortDS
                vi)   alternateMasterPortDS
                vii)  unicastDiscoveryPortDS
                viii) acceptableMasterPortDS
                ix)   L1SyncBasicPortDS
                x)    L1SyncOptParamsPortDS
                xi)   communicationCapabilitiesPortDS
                xii)  performanceMonitoringPortDS
                xiii) slaveMonitoringPortDS
                xiv)  commonServicesPortDS
                xv)   externalPortConfigurationPortDS
        b) transparentClockDefaultDS
        c) transparentClockPortList[]
            1) transparentClockPortDS
        d) commonServices
            1) commonMeanLinkDelayService
                i)  cmldsDefaultDS
                ii) cmldsLinkPortList[]
                    i)   cmldsLinkPortDS
                    ii)  cmldsTimestampCorrectionLinkPortDS
                    iii) cmldsAsymmetryCorrectionLinkPortDS
                    iv)  cmldsPerformanceMonitoringLinkPortDS
        
        Some PTP Profiles have their own MIB modules defined as part of
        the PTP Profile and these MIB modules support access to the
        above data sets. This IEEE1588 MIB module is not intended to
        replace those MIB modules.
        
        The enumerations defined in IEEE Std 1588 contain reserved
        values and values designated for assignment by alternate PTP
        Profiles. The SMIv2 syntax does not allow extending a definition
        of enumerations. As such, a future PTP Profile would not be able
        to provide a meaning to the enumeration values designated for
        assignment by alternate PTP Profiles. To overcome this
        limitation, relevant objects within the IEEE1588 MIB are defined
        as custom types which are based on OBJECT IDENTIFIER type.
        Instead of an integer that can be mapped to an enumeration value
        on the SNMP manager side, the particular object passes an OID to
        an Object within a MIB tree (which may be outside of the
        IEEE1588 MIB), which represents a predefined value. The custom
        types are used to give a hint to implementers that the
        particular OID should return an OID value that represents the
        expected enumeration value. SMIv2 syntax is limited in that it
        does not allow restriction of the set of allowed OIDs. It is up
        to the implementation of an agent to provide the correct value.
        The allowed Objects for each added custom type are placed under
        ieee1588BaseEnum subtree.
        
        Relative to MIB's data model for interface management (IETF RFC
        2863), each PTP Port is a logical access point (see IEEE Std
        1588-2019, 3.1.61), and therefore the PTP Port does not reside
        in the stack of interfaces.
        An SNMP management client will often need to know which specific
        underlying interface is used by a PTP Port. To provide this
        information, the MIB module adds the table ieee1588BasePortTable
        with two mutually excluding means to provide a reference to the
        underlying interface used by the PTP Port:
        1) ieee1588BasePortIfIndex - The underlying IETF interface is
        referenced as an index value (ifIndex) of an interface instance
        in ifTable (defined in IETF RFC 2863). The IETF interface can
        reside at any layer in the interface stack, such as layer 2
        (e.g, IEEE 802.3 Ethernet), or layer 4 (e.g., UDP on IPv4).
        2) ieee1588BasePortIfIndexOid - It is a reference to an index
        value of an interface instance in a table with the definition of
        the used interface. The value of ieee1588BasePortIfIndexOid may
        point to an instance of a vendor specific interface in an
        enterprise MIB.
        For more details please refer to the mentioned OIDs'
        descriptions.
        
        NOTE regarding terminology (two MIB modules):
        To accommodate the need by some organizations to use the
        original terminology specified by IEEE Std 1588, and the need by
        some other organizations to use the alternative terminology
        specified in 4.4 of IEEE Std 1588g-2022, two MIB modules are
        provided by IEEE Std 1588e (MIB and YANG Data Models). For a
        detailed explanation, see 15.3.3.14 of IEEE Std 1588e.
        This module uses the original terminology specified by IEEE Std
        1588 (master/slave)."
        ::= { iso (1) org (3) ieee (111)
              standards-association-numbered-series-standards (2)
              ieee1588 (1588) }
ieee1588MibV1    OBJECT IDENTIFIER ::= { ieee1588 1 }

--=====================================================================
-- Textual Conventions
--=====================================================================


Ieee1588ClockAccuracy ::= TEXTUAL-CONVENTION
    STATUS       current
    DESCRIPTION
        "Clock Accuracy value. The value of this object shall be an
        object from the ieee1588BaseEnumClockAccuracy group."
    REFERENCE    "IEEE 1588-2019: clause  7.6.2.6"
    SYNTAX       OBJECT IDENTIFIER


Ieee1588ClockClass ::= TEXTUAL-CONVENTION
    STATUS       current
    DESCRIPTION
        "Clock Class value. The value of this object shall be an object
        from the ieee1588BaseEnumClockClass group."
    REFERENCE    "IEEE 1588-2019: clause  7.6.2.5"
    SYNTAX       OBJECT IDENTIFIER


Ieee1588ClockIdentity ::= TEXTUAL-CONVENTION
    DISPLAY-HINT "1x:"
    STATUS       current
    DESCRIPTION
        "Identifies unique entities within a PTP Network, e.g. a PTP
        Instance or an entity of a common service.
        The identity is an 8-octet array, constructed according to
        specifications in IEEE Std 1588, using an organization
        identifier from the IEEE Registration Authority."
    REFERENCE    "IEEE 1588-2019: clause  5.3.4, 7.5.2.2"
    SYNTAX       OCTET STRING (SIZE (8))


Ieee1588DelayMechanism ::= TEXTUAL-CONVENTION
    STATUS       current
    DESCRIPTION
        "Enumeration for the path delay mechanism. The value of this
        object shall be an object from the
        ieee1588BaseEnumDelayMechanism group."
    REFERENCE    "IEEE 1588-2019: clause  8.2.15.4.4"
    SYNTAX       OBJECT IDENTIFIER


Ieee1588IfIndexOid ::= TEXTUAL-CONVENTION
    STATUS       current
    DESCRIPTION
        "A reference to an index value with the instance of an
        interface."
    REFERENCE
          "IEEE 1588-2019 as amended by IEEE Std 1588e: clause 15.3.3.8"
    SYNTAX       OBJECT IDENTIFIER


Ieee1588InstanceType ::= TEXTUAL-CONVENTION
    STATUS       current
    DESCRIPTION
        "Enumeration for the type of PTP Instance. The value of this
        object shall be an object from the ieee1588BaseEnumInstanceType
        group."
    REFERENCE    "IEEE 1588-2019: clause  8.2.1.5.5"
    SYNTAX       OBJECT IDENTIFIER


Ieee1588L1SyncState ::= TEXTUAL-CONVENTION
    STATUS       current
    DESCRIPTION
        "Enumeration for states of the L1Sync state machine associated
        with an L1Sync port. The value of this object shall be an object
        from the Ieee1588BaseEnumL1SyncState group."
    REFERENCE    "IEEE 1588-2019: clause  L.5.3.5"
    SYNTAX       OBJECT IDENTIFIER


Ieee1588LogTimeInterval ::= TEXTUAL-CONVENTION
    DISPLAY-HINT "d"
    STATUS       current
    DESCRIPTION
        "Time interval expressed as logarithm base 2 of the number of
        seconds, e.g. 0 = 1s, 2 = 4s, -3 = 125ms."
    REFERENCE    "IEEE 1588-2019: clause  7.7.2.1"
    SYNTAX       Integer32 (-128..127)


Ieee1588MessageType ::= TEXTUAL-CONVENTION
    STATUS       current
    DESCRIPTION
        "Enumeration for the type of the PTP message. The value of this
        object shall be an object from the ieee1588BaseEnumMessageType
        Group."
    REFERENCE    "IEEE 1588-2019: clause  13.3.2.3"
    SYNTAX       OBJECT IDENTIFIER


Ieee1588NetworkProtocol ::= TEXTUAL-CONVENTION
    STATUS       current
    DESCRIPTION
        "Enumeration for the protocol used by a PTP Instance to
        transport PTP messages. The value of this object shall be an
        object from the ieee1588BaseEnumNetworkProtocol Group."
    REFERENCE    "IEEE 1588-2019: clause  7.4.1"
    SYNTAX       OBJECT IDENTIFIER


Ieee1588PortState ::= TEXTUAL-CONVENTION
    STATUS       current
    DESCRIPTION
        "Enumeration for the state of the PTP protocol engine associated
        with the PTP Port. The value of this object shall be an object
        from the ieee1588BaseEnumPortState Group."
    REFERENCE    "IEEE 1588-2019: clause  8.2.15.3.1, 9.2.5"
    SYNTAX       OBJECT IDENTIFIER


Ieee1588RelativeDifference ::= TEXTUAL-CONVENTION
    DISPLAY-HINT "8d"
    STATUS       current
    DESCRIPTION
        "Integer64, the value is the relative difference expressed as a
        dimensionless fraction and multiplied by 2^62, with any
        remaining fractional part truncated."
    REFERENCE    "IEEE 1588-2019: clause  5.3.11"
    SYNTAX       OCTET STRING (SIZE (8))


Ieee1588SeverityCode ::= TEXTUAL-CONVENTION
    STATUS       current
    DESCRIPTION
        "Enumeration for the severity of a fault record. The value of
        this object shall be an object from the
        ieee1588BaseEnumSeverityCode Group."
    REFERENCE    "IEEE 1588-2019: clause  8.2.6.3"
    SYNTAX       OBJECT IDENTIFIER


Ieee1588TimeInterval ::= TEXTUAL-CONVENTION
    DISPLAY-HINT "2x:"
    STATUS       current
    DESCRIPTION
        "Integer64, timeInterval value in scaled nanoseconds. This value
        is the time interval expressed in nanoseconds, multiplied by
        2^16. Positive or negative time intervals outside the maximum
        range of this data type shall be encoded as the largest positive
        and negative values of the data type, respectively."
    REFERENCE    "IEEE 1588-2019: clause  5.3.2"
    SYNTAX       OCTET STRING (SIZE (8))


Ieee1588TimeSource ::= TEXTUAL-CONVENTION
    STATUS       current
    DESCRIPTION
        "Enumeration for the timeSource. It is an information-only
        attribute indicating the type of source of time used by a
        Grandmaster Clock. The value of this object shall be an object
        from the ieee1588BaseEnumTimeSource Group."
    REFERENCE    "IEEE 1588-2019: clause  7.6.2.8"
    SYNTAX       OBJECT IDENTIFIER


UInteger48 ::= TEXTUAL-CONVENTION
    DISPLAY-HINT "12d"
    STATUS       current
    DESCRIPTION
        "48bit unsigned integer value"
    REFERENCE    "IEEE 1588-2019: clause  5.2"
    SYNTAX       OCTET STRING (SIZE (6))


--=====================================================================
-- Events
--=====================================================================

-- The current version of this MIB does not support events. This branch
-- is not used but is kept as a placeholder for future releases.
ieee1588Notifications OBJECT IDENTIFIER ::= { ieee1588MibV1 0 }

--=====================================================================
-- Data Sets
--=====================================================================


ieee1588Objects OBJECT IDENTIFIER ::= { ieee1588MibV1 1 }

ieee1588Base OBJECT IDENTIFIER ::= { ieee1588Objects 1 }

ieee1588BaseInstanceTable OBJECT-TYPE
    SYNTAX       SEQUENCE OF Ieee1588BaseInstanceEntry
    MAX-ACCESS   not-accessible
    STATUS       current
    DESCRIPTION
        "This table lists PTP Instances in the PTP Node. This table is
        used to allow for dynamic creation and deletion of PTP Instances
        in implementations that support it."
    REFERENCE    "IEEE 1588-2019: clause 6.1.3, 7.6"
    ::= { ieee1588Base 1 }
-- .1.1

ieee1588BaseInstanceEntry OBJECT-TYPE
    SYNTAX       Ieee1588BaseInstanceEntry
    MAX-ACCESS   not-accessible
    STATUS       current
    DESCRIPTION
        "An Entry representing a PTP Instance. Each PTP Instance
        represents a distinct instance of PTP implementation (i.e.
        distinct Ordinary Clock, Boundary Clock, or Transparent Clock),
        maintaining a distinct time. PTP Instances may be created or
        deleted dynamically in implementations that support dynamic
        create/delete."
    REFERENCE    "IEEE 1588-2019: clause 6.1.3, 7.6"
    INDEX        {
        ieee1588InstanceIndex }
    ::= { ieee1588BaseInstanceTable 1 }
-- .1.1.1


Ieee1588BaseInstanceEntry    ::= SEQUENCE {
        ieee1588InstanceIndex                   Unsigned32,
        ieee1588BaseInstanceRowStatus           RowStatus,
        ieee1588BaseInstanceName                SnmpAdminString
        }

ieee1588InstanceIndex OBJECT-TYPE
    SYNTAX       Unsigned32(1..65534)
    MAX-ACCESS   not-accessible
    STATUS       current
    DESCRIPTION
        "An numeric index identifying a specific PTP Instance. A numeric
        index is used instead of ClockIdentify to identify a specific
        PTP Instance."
    ::= { ieee1588BaseInstanceEntry 1 }
-- .1.1.1.1

ieee1588BaseInstanceRowStatus OBJECT-TYPE
    SYNTAX       RowStatus
    MAX-ACCESS   read-create
    STATUS       current
    DESCRIPTION
        "This object is used to create and delete PTP Instances."
    ::= { ieee1588BaseInstanceEntry 2 }
-- .1.1.1.2

ieee1588BaseInstanceName OBJECT-TYPE
    SYNTAX       SnmpAdminString
    MAX-ACCESS   read-create
    STATUS       current
    DESCRIPTION
        "Name for identification of a PTP Instance. Used only for
        management."
    ::= { ieee1588BaseInstanceEntry 3 }
-- .1.1.1.3

ieee1588BasePortTable OBJECT-TYPE
    SYNTAX       SEQUENCE OF Ieee1588BasePortEntry
    MAX-ACCESS   not-accessible
    STATUS       current
    DESCRIPTION
        "This table contains mapping between ieee1588PortIndex
        (associated with a PTP Port or Common Service Port) used within
        a PTP Instance into a physical port index."
    ::= { ieee1588Base 2 }
-- .1.2

ieee1588BasePortEntry OBJECT-TYPE
    SYNTAX       Ieee1588BasePortEntry
    MAX-ACCESS   not-accessible
    STATUS       current
    DESCRIPTION
        "An Entry representing a PTP Port"
    INDEX        {
        ieee1588InstanceIndex,
        ieee1588PortIndex }
    ::= { ieee1588BasePortTable 1 }
-- .1.2.1


Ieee1588BasePortEntry    ::= SEQUENCE {
        ieee1588PortIndex                       Unsigned32,
        ieee1588BasePortRowStatus               RowStatus,
        ieee1588BasePortIfIndex                 InterfaceIndexOrZero,
        ieee1588BasePortIfIndexOid              Ieee1588IfIndexOid
        }

ieee1588PortIndex OBJECT-TYPE
    SYNTAX       Unsigned32(1..65534)
    MAX-ACCESS   not-accessible
    STATUS       current
    DESCRIPTION
        "An index that is unique per PTP Port within the PTP Instance,
        applicable to the management context only (i.e. not used in PTP
        Messages). NOTE: this number might not be equivalent to the
        portNumber attribute (portDS.portIdentity.portNumber data set
        member)."
    REFERENCE    "IEEE 1588-2019: clause 7.5.2.3"
    ::= { ieee1588BasePortEntry 2 }
-- .1.2.1.2

ieee1588BasePortRowStatus OBJECT-TYPE
    SYNTAX       RowStatus
    MAX-ACCESS   read-create
    STATUS       current
    DESCRIPTION
        "This object is used to create and delete PTP Ports."
    ::= { ieee1588BasePortEntry 3 }
-- .1.2.1.3

ieee1588BasePortIfIndex OBJECT-TYPE
    SYNTAX       InterfaceIndexOrZero
    MAX-ACCESS   read-create
    STATUS       current
    DESCRIPTION
        "This value can be used to identify the interface used by the
        respective PTP Port.
        If this value is non-zero, it refers to the ifIndex object of
        the used interface in the ifTable (IF-MIB). If this value is
        zero, the ifIndex object is not used and
        ieee1588BasePortIfIndexOid can reference the interface used by
        this PTP Port. If this value is zero and Ieee1588IfIndexOid is
        zeroDotZero or is not defined then PTP Port has no defined
        underlying interface."
    REFERENCE
          "IEEE 1588-2019 as amended by IEEE Std 1588e: clause 15.3.3.8"
    ::= { ieee1588BasePortEntry 4 }
-- .1.2.1.4

ieee1588BasePortIfIndexOid OBJECT-TYPE
    SYNTAX       Ieee1588IfIndexOid
    MAX-ACCESS   read-create
    STATUS       current
    DESCRIPTION
        "This OID can be used to identify the interface of the
        respective PTP Port, if the value of ieee1588BasePortIfIndex is
        zero. The value of this object references the index of the used
        interface. If ieee1588BasePortIfIndex is set to a non-zero
        value, the value of this OID is not used."
    REFERENCE
          "IEEE 1588-2019 as amended by IEEE Std 1588e: clause 15.3.3.8"
    ::= { ieee1588BasePortEntry 5 }
-- .1.2.1.5

-- Maps enumerate values defined in the standard into OIDs
ieee1588BaseEnum OBJECT IDENTIFIER ::= { ieee1588Base 3 }

-- Group contains enumeration of Clock Accuracy values from IEEE Std
-- 1588-2019 7.6.2.6, with the unused ranges of values:
-- 0..22 - Reserved
-- 50..127 - Reserved
-- 255 – Reserved
ieee1588BaseEnumClockAccuracy
                            OBJECT IDENTIFIER ::= { ieee1588BaseEnum 1 }

ieee1588BaseEnumCaTimeAccurateTo1000fs OBJECT-IDENTITY
    STATUS       current
    DESCRIPTION
        "ClockAccuracy 0x17: The time is accurate to within 1 ps."
    REFERENCE    "IEEE 1588-2019: clause 7.6.2.6"
    ::= { ieee1588BaseEnumClockAccuracy 23 }

ieee1588BaseEnumCaTimeAccurateTo2500fs OBJECT-IDENTITY
    STATUS       current
    DESCRIPTION
        "ClockAccuracy 0x18: The time is accurate to within 2.5 ps."
    REFERENCE    "IEEE 1588-2019: clause 7.6.2.6"
    ::= { ieee1588BaseEnumClockAccuracy 24 }

ieee1588BaseEnumCaTimeAccurateTo10ps OBJECT-IDENTITY
    STATUS       current
    DESCRIPTION
        "ClockAccuracy 0x19: The time is accurate to within 10 ps."
    REFERENCE    "IEEE 1588-2019: clause 7.6.2.6"
    ::= { ieee1588BaseEnumClockAccuracy 25 }

ieee1588BaseEnumCaTimeAccurateTo25ps OBJECT-IDENTITY
    STATUS       current
    DESCRIPTION
        "ClockAccuracy 0x1A: The time is accurate to within 25 ps."
    REFERENCE    "IEEE 1588-2019: clause 7.6.2.6"
    ::= { ieee1588BaseEnumClockAccuracy 26 }

ieee1588BaseEnumCaTimeAccurateTo100ps OBJECT-IDENTITY
    STATUS       current
    DESCRIPTION
        "ClockAccuracy 0x1B: The time is accurate to within 100 ps."
    REFERENCE    "IEEE 1588-2019: clause 7.6.2.6"
    ::= { ieee1588BaseEnumClockAccuracy 27 }

ieee1588BaseEnumCaTimeAccurateTo250ps OBJECT-IDENTITY
    STATUS       current
    DESCRIPTION
        "ClockAccuracy 0x1C: The time is accurate to within 250 ps."
    REFERENCE    "IEEE 1588-2019: clause 7.6.2.6"
    ::= { ieee1588BaseEnumClockAccuracy 28 }

ieee1588BaseEnumCaTimeAccurateTo1000ps OBJECT-IDENTITY
    STATUS       current
    DESCRIPTION
        "ClockAccuracy 0x1D: The time is accurate to within 1 ns."
    REFERENCE    "IEEE 1588-2019: clause 7.6.2.6"
    ::= { ieee1588BaseEnumClockAccuracy 29 }

ieee1588BaseEnumCaTimeAccurateTo2500ps OBJECT-IDENTITY
    STATUS       current
    DESCRIPTION
        "ClockAccuracy 0x1E: The time is accurate to within 2.5 ns."
    REFERENCE    "IEEE 1588-2019: clause 7.6.2.6"
    ::= { ieee1588BaseEnumClockAccuracy 30 }

ieee1588BaseEnumCaTimeAccurateTo10ns OBJECT-IDENTITY
    STATUS       current
    DESCRIPTION
        "ClockAccuracy 0x1F: The time is accurate to within 10 ns."
    REFERENCE    "IEEE 1588-2019: clause 7.6.2.6"
    ::= { ieee1588BaseEnumClockAccuracy 31 }

ieee1588BaseEnumCaTimeAccurateTo25ns OBJECT-IDENTITY
    STATUS       current
    DESCRIPTION
        "ClockAccuracy 0x20: The time is accurate to within 25 ns."
    REFERENCE    "IEEE 1588-2019: clause 7.6.2.6"
    ::= { ieee1588BaseEnumClockAccuracy 32 }

ieee1588BaseEnumCaTimeAccurateTo100ns OBJECT-IDENTITY
    STATUS       current
    DESCRIPTION
        "ClockAccuracy 0x21: The time is accurate to within 100 ns."
    REFERENCE    "IEEE 1588-2019: clause 7.6.2.6"
    ::= { ieee1588BaseEnumClockAccuracy 33 }

ieee1588BaseEnumCaTimeAccurateTo250ns OBJECT-IDENTITY
    STATUS       current
    DESCRIPTION
        "ClockAccuracy 0x22: The time is accurate to within 250 ns."
    REFERENCE    "IEEE 1588-2019: clause 7.6.2.6"
    ::= { ieee1588BaseEnumClockAccuracy 34 }

ieee1588BaseEnumCaTimeAccurateTo1000ns OBJECT-IDENTITY
    STATUS       current
    DESCRIPTION
        "ClockAccuracy 0x23: The time is accurate to within 1 us."
    REFERENCE    "IEEE 1588-2019: clause 7.6.2.6"
    ::= { ieee1588BaseEnumClockAccuracy 35 }

ieee1588BaseEnumCaTimeAccurateTo2500ns OBJECT-IDENTITY
    STATUS       current
    DESCRIPTION
        "ClockAccuracy 0x24: The time is accurate to within 2.5 us."
    REFERENCE    "IEEE 1588-2019: clause 7.6.2.6"
    ::= { ieee1588BaseEnumClockAccuracy 36 }

ieee1588BaseEnumCaTimeAccurateTo10us OBJECT-IDENTITY
    STATUS       current
    DESCRIPTION
        "ClockAccuracy 0x25: The time is accurate to within 10 us."
    REFERENCE    "IEEE 1588-2019: clause 7.6.2.6"
    ::= { ieee1588BaseEnumClockAccuracy 37 }

ieee1588BaseEnumCaTimeAccurateTo25us OBJECT-IDENTITY
    STATUS       current
    DESCRIPTION
        "ClockAccuracy 0x26: The time is accurate to within 25 us."
    REFERENCE    "IEEE 1588-2019: clause 7.6.2.6"
    ::= { ieee1588BaseEnumClockAccuracy 38 }

ieee1588BaseEnumCaTimeAccurateTo100us OBJECT-IDENTITY
    STATUS       current
    DESCRIPTION
        "ClockAccuracy 0x27: The time is accurate to within 100 us."
    REFERENCE    "IEEE 1588-2019: clause 7.6.2.6"
    ::= { ieee1588BaseEnumClockAccuracy 39 }

ieee1588BaseEnumCaTimeAccurateTo250us OBJECT-IDENTITY
    STATUS       current
    DESCRIPTION
        "ClockAccuracy 0x28: The time is accurate to within 250 us."
    REFERENCE    "IEEE 1588-2019: clause 7.6.2.6"
    ::= { ieee1588BaseEnumClockAccuracy 40 }

ieee1588BaseEnumCaTimeAccurateTo1000us OBJECT-IDENTITY
    STATUS       current
    DESCRIPTION
        "ClockAccuracy 0x29: The time is accurate to within 1 ms."
    REFERENCE    "IEEE 1588-2019: clause 7.6.2.6"
    ::= { ieee1588BaseEnumClockAccuracy 41 }

ieee1588BaseEnumCaTimeAccurateTo2500us OBJECT-IDENTITY
    STATUS       current
    DESCRIPTION
        "ClockAccuracy 0x2A: The time is accurate to within 2.5 ms."
    REFERENCE    "IEEE 1588-2019: clause 7.6.2.6"
    ::= { ieee1588BaseEnumClockAccuracy 42 }

ieee1588BaseEnumCaTimeAccurateTo10ms OBJECT-IDENTITY
    STATUS       current
    DESCRIPTION
        "ClockAccuracy 0x2B: The time is accurate to within 10 ms."
    REFERENCE    "IEEE 1588-2019: clause 7.6.2.6"
    ::= { ieee1588BaseEnumClockAccuracy 43 }

ieee1588BaseEnumCaTimeAccurateTo25ms OBJECT-IDENTITY
    STATUS       current
    DESCRIPTION
        "ClockAccuracy 0x2C: The time is accurate to within 25 ms."
    REFERENCE    "IEEE 1588-2019: clause 7.6.2.6"
    ::= { ieee1588BaseEnumClockAccuracy 44 }

ieee1588BaseEnumCaTimeAccurateTo100ms OBJECT-IDENTITY
    STATUS       current
    DESCRIPTION
        "ClockAccuracy 0x2D: The time is accurate to within 100 ms."
    REFERENCE    "IEEE 1588-2019: clause 7.6.2.6"
    ::= { ieee1588BaseEnumClockAccuracy 45 }

ieee1588BaseEnumCaTimeAccurateTo250ms OBJECT-IDENTITY
    STATUS       current
    DESCRIPTION
        "ClockAccuracy 0x2E: The time is accurate to within 250 ms."
    REFERENCE    "IEEE 1588-2019: clause 7.6.2.6"
    ::= { ieee1588BaseEnumClockAccuracy 46 }

ieee1588BaseEnumCaTimeAccurateTo1s OBJECT-IDENTITY
    STATUS       current
    DESCRIPTION
        "ClockAccuracy 0x2F: The time is accurate to within 1 s."
    REFERENCE    "IEEE 1588-2019: clause 7.6.2.6"
    ::= { ieee1588BaseEnumClockAccuracy 47 }

ieee1588BaseEnumCaTimeAccurateTo10s OBJECT-IDENTITY
    STATUS       current
    DESCRIPTION
        "ClockAccuracy 0x30: The time is accurate to within 10 s."
    REFERENCE    "IEEE 1588-2019: clause 7.6.2.6"
    ::= { ieee1588BaseEnumClockAccuracy 48 }

ieee1588BaseEnumCaTimeAccurateToGT10s OBJECT-IDENTITY
    STATUS       current
    DESCRIPTION
        "ClockAccuracy 0x31: The time accuracy exceeds 10s."
    REFERENCE    "IEEE 1588-2019: clause 7.6.2.6"
    ::= { ieee1588BaseEnumClockAccuracy 49 }

ieee1588BaseEnumCaAltPtpProfile128 OBJECT-IDENTITY
    STATUS       current
    DESCRIPTION
        "ClockAccuracy 0x80: Designated for assignment by alternate PTP
        Profiles"
    REFERENCE    "IEEE 1588-2019: clause 7.6.2.6"
    ::= { ieee1588BaseEnumClockAccuracy 128 }

ieee1588BaseEnumCaAltPtpProfile129 OBJECT-IDENTITY
    STATUS       current
    DESCRIPTION
        "ClockAccuracy 0x81: Designated for assignment by alternate PTP
        Profiles"
    REFERENCE    "IEEE 1588-2019: clause 7.6.2.6"
    ::= { ieee1588BaseEnumClockAccuracy 129 }

ieee1588BaseEnumCaAltPtpProfile130 OBJECT-IDENTITY
    STATUS       current
    DESCRIPTION
        "ClockAccuracy 0x82: Designated for assignment by alternate PTP
        Profiles"
    REFERENCE    "IEEE 1588-2019: clause 7.6.2.6"
    ::= { ieee1588BaseEnumClockAccuracy 130 }

ieee1588BaseEnumCaAltPtpProfile131 OBJECT-IDENTITY
    STATUS       current
    DESCRIPTION
        "ClockAccuracy 0x83: Designated for assignment by alternate PTP
        Profiles"
    REFERENCE    "IEEE 1588-2019: clause 7.6.2.6"
    ::= { ieee1588BaseEnumClockAccuracy 131 }

ieee1588BaseEnumCaAltPtpProfile132 OBJECT-IDENTITY
    STATUS       current
    DESCRIPTION
        "ClockAccuracy 0x84: Designated for assignment by alternate PTP
        Profiles"
    REFERENCE    "IEEE 1588-2019: clause 7.6.2.6"
    ::= { ieee1588BaseEnumClockAccuracy 132 }

ieee1588BaseEnumCaAltPtpProfile133 OBJECT-IDENTITY
    STATUS       current
    DESCRIPTION
        "ClockAccuracy 0x85: Designated for assignment by alternate PTP
        Profiles"
    REFERENCE    "IEEE 1588-2019: clause 7.6.2.6"
    ::= { ieee1588BaseEnumClockAccuracy 133 }

ieee1588BaseEnumCaAltPtpProfile134 OBJECT-IDENTITY
    STATUS       current
    DESCRIPTION
        "ClockAccuracy 0x86: Designated for assignment by alternate PTP
        Profiles"
    REFERENCE    "IEEE 1588-2019: clause 7.6.2.6"
    ::= { ieee1588BaseEnumClockAccuracy 134 }

ieee1588BaseEnumCaAltPtpProfile135 OBJECT-IDENTITY
    STATUS       current
    DESCRIPTION
        "ClockAccuracy 0x87: Designated for assignment by alternate PTP
        Profiles"
    REFERENCE    "IEEE 1588-2019: clause 7.6.2.6"
    ::= { ieee1588BaseEnumClockAccuracy 135 }

ieee1588BaseEnumCaAltPtpProfile136 OBJECT-IDENTITY
    STATUS       current
    DESCRIPTION
        "ClockAccuracy 0x88: Designated for assignment by alternate PTP
        Profiles"
    REFERENCE    "IEEE 1588-2019: clause 7.6.2.6"
    ::= { ieee1588BaseEnumClockAccuracy 136 }

ieee1588BaseEnumCaAltPtpProfile137 OBJECT-IDENTITY
    STATUS       current
    DESCRIPTION
        "ClockAccuracy 0x89: Designated for assignment by alternate PTP
        Profiles"
    REFERENCE    "IEEE 1588-2019: clause 7.6.2.6"
    ::= { ieee1588BaseEnumClockAccuracy 137 }

ieee1588BaseEnumCaAltPtpProfile138 OBJECT-IDENTITY
    STATUS       current
    DESCRIPTION
        "ClockAccuracy 0x8A: Designated for assignment by alternate PTP
        Profiles"
    REFERENCE    "IEEE 1588-2019: clause 7.6.2.6"
    ::= { ieee1588BaseEnumClockAccuracy 138 }

ieee1588BaseEnumCaAltPtpProfile139 OBJECT-IDENTITY
    STATUS       current
    DESCRIPTION
        "ClockAccuracy 0x8B: Designated for assignment by alternate PTP
        Profiles"
    REFERENCE    "IEEE 1588-2019: clause 7.6.2.6"
    ::= { ieee1588BaseEnumClockAccuracy 139 }

ieee1588BaseEnumCaAltPtpProfile140 OBJECT-IDENTITY
    STATUS       current
    DESCRIPTION
        "ClockAccuracy 0x8C: Designated for assignment by alternate PTP
        Profiles"
    REFERENCE    "IEEE 1588-2019: clause 7.6.2.6"
    ::= { ieee1588BaseEnumClockAccuracy 140 }

ieee1588BaseEnumCaAltPtpProfile141 OBJECT-IDENTITY
    STATUS       current
    DESCRIPTION
        "ClockAccuracy 0x8D: Designated for assignment by alternate PTP
        Profiles"
    REFERENCE    "IEEE 1588-2019: clause 7.6.2.6"
    ::= { ieee1588BaseEnumClockAccuracy 141 }

ieee1588BaseEnumCaAltPtpProfile142 OBJECT-IDENTITY
    STATUS       current
    DESCRIPTION
        "ClockAccuracy 0x8E: Designated for assignment by alternate PTP
        Profiles"
    REFERENCE    "IEEE 1588-2019: clause 7.6.2.6"
    ::= { ieee1588BaseEnumClockAccuracy 142 }

ieee1588BaseEnumCaAltPtpProfile143 OBJECT-IDENTITY
    STATUS       current
    DESCRIPTION
        "ClockAccuracy 0x8F: Designated for assignment by alternate PTP
        Profiles"
    REFERENCE    "IEEE 1588-2019: clause 7.6.2.6"
    ::= { ieee1588BaseEnumClockAccuracy 143 }

ieee1588BaseEnumCaAltPtpProfile144 OBJECT-IDENTITY
    STATUS       current
    DESCRIPTION
        "ClockAccuracy 0x90: Designated for assignment by alternate PTP
        Profiles"
    REFERENCE    "IEEE 1588-2019: clause 7.6.2.6"
    ::= { ieee1588BaseEnumClockAccuracy 144 }

ieee1588BaseEnumCaAltPtpProfile145 OBJECT-IDENTITY
    STATUS       current
    DESCRIPTION
        "ClockAccuracy 0x91: Designated for assignment by alternate PTP
        Profiles"
    REFERENCE    "IEEE 1588-2019: clause 7.6.2.6"
    ::= { ieee1588BaseEnumClockAccuracy 145 }

ieee1588BaseEnumCaAltPtpProfile146 OBJECT-IDENTITY
    STATUS       current
    DESCRIPTION
        "ClockAccuracy 0x92: Designated for assignment by alternate PTP
        Profiles"
    REFERENCE    "IEEE 1588-2019: clause 7.6.2.6"
    ::= { ieee1588BaseEnumClockAccuracy 146 }

ieee1588BaseEnumCaAltPtpProfile147 OBJECT-IDENTITY
    STATUS       current
    DESCRIPTION
        "ClockAccuracy 0x93: Designated for assignment by alternate PTP
        Profiles"
    REFERENCE    "IEEE 1588-2019: clause 7.6.2.6"
    ::= { ieee1588BaseEnumClockAccuracy 147 }

ieee1588BaseEnumCaAltPtpProfile148 OBJECT-IDENTITY
    STATUS       current
    DESCRIPTION
        "ClockAccuracy 0x94: Designated for assignment by alternate PTP
        Profiles"
    REFERENCE    "IEEE 1588-2019: clause 7.6.2.6"
    ::= { ieee1588BaseEnumClockAccuracy 148 }

ieee1588BaseEnumCaAltPtpProfile149 OBJECT-IDENTITY
    STATUS       current
    DESCRIPTION
        "ClockAccuracy 0x95: Designated for assignment by alternate PTP
        Profiles"
    REFERENCE    "IEEE 1588-2019: clause 7.6.2.6"
    ::= { ieee1588BaseEnumClockAccuracy 149 }

ieee1588BaseEnumCaAltPtpProfile150 OBJECT-IDENTITY
    STATUS       current
    DESCRIPTION
        "ClockAccuracy 0x96: Designated for assignment by alternate PTP
        Profiles"
    REFERENCE    "IEEE 1588-2019: clause 7.6.2.6"
    ::= { ieee1588BaseEnumClockAccuracy 150 }

ieee1588BaseEnumCaAltPtpProfile151 OBJECT-IDENTITY
    STATUS       current
    DESCRIPTION
        "ClockAccuracy 0x97: Designated for assignment by alternate PTP
        Profiles"
    REFERENCE    "IEEE 1588-2019: clause 7.6.2.6"
    ::= { ieee1588BaseEnumClockAccuracy 151 }

ieee1588BaseEnumCaAltPtpProfile152 OBJECT-IDENTITY
    STATUS       current
    DESCRIPTION
        "ClockAccuracy 0x98: Designated for assignment by alternate PTP
        Profiles"
    REFERENCE    "IEEE 1588-2019: clause 7.6.2.6"
    ::= { ieee1588BaseEnumClockAccuracy 152 }

ieee1588BaseEnumCaAltPtpProfile153 OBJECT-IDENTITY
    STATUS       current
    DESCRIPTION
        "ClockAccuracy 0x99: Designated for assignment by alternate PTP
        Profiles"
    REFERENCE    "IEEE 1588-2019: clause 7.6.2.6"
    ::= { ieee1588BaseEnumClockAccuracy 153 }

ieee1588BaseEnumCaAltPtpProfile154 OBJECT-IDENTITY
    STATUS       current
    DESCRIPTION
        "ClockAccuracy 0x9A: Designated for assignment by alternate PTP
        Profiles"
    REFERENCE    "IEEE 1588-2019: clause 7.6.2.6"
    ::= { ieee1588BaseEnumClockAccuracy 154 }

ieee1588BaseEnumCaAltPtpProfile155 OBJECT-IDENTITY
    STATUS       current
    DESCRIPTION
        "ClockAccuracy 0x9B: Designated for assignment by alternate PTP
        Profiles"
    REFERENCE    "IEEE 1588-2019: clause 7.6.2.6"
    ::= { ieee1588BaseEnumClockAccuracy 155 }

ieee1588BaseEnumCaAltPtpProfile156 OBJECT-IDENTITY
    STATUS       current
    DESCRIPTION
        "ClockAccuracy 0x9C: Designated for assignment by alternate PTP
        Profiles"
    REFERENCE    "IEEE 1588-2019: clause 7.6.2.6"
    ::= { ieee1588BaseEnumClockAccuracy 156 }

ieee1588BaseEnumCaAltPtpProfile157 OBJECT-IDENTITY
    STATUS       current
    DESCRIPTION
        "ClockAccuracy 0x9D: Designated for assignment by alternate PTP
        Profiles"
    REFERENCE    "IEEE 1588-2019: clause 7.6.2.6"
    ::= { ieee1588BaseEnumClockAccuracy 157 }

ieee1588BaseEnumCaAltPtpProfile158 OBJECT-IDENTITY
    STATUS       current
    DESCRIPTION
        "ClockAccuracy 0x9E: Designated for assignment by alternate PTP
        Profiles"
    REFERENCE    "IEEE 1588-2019: clause 7.6.2.6"
    ::= { ieee1588BaseEnumClockAccuracy 158 }

ieee1588BaseEnumCaAltPtpProfile159 OBJECT-IDENTITY
    STATUS       current
    DESCRIPTION
        "ClockAccuracy 0x9F: Designated for assignment by alternate PTP
        Profiles"
    REFERENCE    "IEEE 1588-2019: clause 7.6.2.6"
    ::= { ieee1588BaseEnumClockAccuracy 159 }

ieee1588BaseEnumCaAltPtpProfile160 OBJECT-IDENTITY
    STATUS       current
    DESCRIPTION
        "ClockAccuracy 0xA0: Designated for assignment by alternate PTP
        Profiles"
    REFERENCE    "IEEE 1588-2019: clause 7.6.2.6"
    ::= { ieee1588BaseEnumClockAccuracy 160 }

ieee1588BaseEnumCaAltPtpProfile161 OBJECT-IDENTITY
    STATUS       current
    DESCRIPTION
        "ClockAccuracy 0xA1: Designated for assignment by alternate PTP
        Profiles"
    REFERENCE    "IEEE 1588-2019: clause 7.6.2.6"
    ::= { ieee1588BaseEnumClockAccuracy 161 }

ieee1588BaseEnumCaAltPtpProfile162 OBJECT-IDENTITY
    STATUS       current
    DESCRIPTION
        "ClockAccuracy 0xA2: Designated for assignment by alternate PTP
        Profiles"
    REFERENCE    "IEEE 1588-2019: clause 7.6.2.6"
    ::= { ieee1588BaseEnumClockAccuracy 162 }

ieee1588BaseEnumCaAltPtpProfile163 OBJECT-IDENTITY
    STATUS       current
    DESCRIPTION
        "ClockAccuracy 0xA3: Designated for assignment by alternate PTP
        Profiles"
    REFERENCE    "IEEE 1588-2019: clause 7.6.2.6"
    ::= { ieee1588BaseEnumClockAccuracy 163 }

ieee1588BaseEnumCaAltPtpProfile164 OBJECT-IDENTITY
    STATUS       current
    DESCRIPTION
        "ClockAccuracy 0xA4: Designated for assignment by alternate PTP
        Profiles"
    REFERENCE    "IEEE 1588-2019: clause 7.6.2.6"
    ::= { ieee1588BaseEnumClockAccuracy 164 }

ieee1588BaseEnumCaAltPtpProfile165 OBJECT-IDENTITY
    STATUS       current
    DESCRIPTION
        "ClockAccuracy 0xA5: Designated for assignment by alternate PTP
        Profiles"
    REFERENCE    "IEEE 1588-2019: clause 7.6.2.6"
    ::= { ieee1588BaseEnumClockAccuracy 165 }

ieee1588BaseEnumCaAltPtpProfile166 OBJECT-IDENTITY
    STATUS       current
    DESCRIPTION
        "ClockAccuracy 0xA6: Designated for assignment by alternate PTP
        Profiles"
    REFERENCE    "IEEE 1588-2019: clause 7.6.2.6"
    ::= { ieee1588BaseEnumClockAccuracy 166 }

ieee1588BaseEnumCaAltPtpProfile167 OBJECT-IDENTITY
    STATUS       current
    DESCRIPTION
        "ClockAccuracy 0xA7: Designated for assignment by alternate PTP
        Profiles"
    REFERENCE    "IEEE 1588-2019: clause 7.6.2.6"
    ::= { ieee1588BaseEnumClockAccuracy 167 }

ieee1588BaseEnumCaAltPtpProfile168 OBJECT-IDENTITY
    STATUS       current
    DESCRIPTION
        "ClockAccuracy 0xA8: Designated for assignment by alternate PTP
        Profiles"
    REFERENCE    "IEEE 1588-2019: clause 7.6.2.6"
    ::= { ieee1588BaseEnumClockAccuracy 168 }

ieee1588BaseEnumCaAltPtpProfile169 OBJECT-IDENTITY
    STATUS       current
    DESCRIPTION
        "ClockAccuracy 0xA9: Designated for assignment by alternate PTP
        Profiles"
    REFERENCE    "IEEE 1588-2019: clause 7.6.2.6"
    ::= { ieee1588BaseEnumClockAccuracy 169 }

ieee1588BaseEnumCaAltPtpProfile170 OBJECT-IDENTITY
    STATUS       current
    DESCRIPTION
        "ClockAccuracy 0xAA: Designated for assignment by alternate PTP
        Profiles"
    REFERENCE    "IEEE 1588-2019: clause 7.6.2.6"
    ::= { ieee1588BaseEnumClockAccuracy 170 }

ieee1588BaseEnumCaAltPtpProfile171 OBJECT-IDENTITY
    STATUS       current
    DESCRIPTION
        "ClockAccuracy 0xAB: Designated for assignment by alternate PTP
        Profiles"
    REFERENCE    "IEEE 1588-2019: clause 7.6.2.6"
    ::= { ieee1588BaseEnumClockAccuracy 171 }

ieee1588BaseEnumCaAltPtpProfile172 OBJECT-IDENTITY
    STATUS       current
    DESCRIPTION
        "ClockAccuracy 0xAC: Designated for assignment by alternate PTP
        Profiles"
    REFERENCE    "IEEE 1588-2019: clause 7.6.2.6"
    ::= { ieee1588BaseEnumClockAccuracy 172 }

ieee1588BaseEnumCaAltPtpProfile173 OBJECT-IDENTITY
    STATUS       current
    DESCRIPTION
        "ClockAccuracy 0xAD: Designated for assignment by alternate PTP
        Profiles"
    REFERENCE    "IEEE 1588-2019: clause 7.6.2.6"
    ::= { ieee1588BaseEnumClockAccuracy 173 }

ieee1588BaseEnumCaAltPtpProfile174 OBJECT-IDENTITY
    STATUS       current
    DESCRIPTION
        "ClockAccuracy 0xAE: Designated for assignment by alternate PTP
        Profiles"
    REFERENCE    "IEEE 1588-2019: clause 7.6.2.6"
    ::= { ieee1588BaseEnumClockAccuracy 174 }

ieee1588BaseEnumCaAltPtpProfile175 OBJECT-IDENTITY
    STATUS       current
    DESCRIPTION
        "ClockAccuracy 0xAF: Designated for assignment by alternate PTP
        Profiles"
    REFERENCE    "IEEE 1588-2019: clause 7.6.2.6"
    ::= { ieee1588BaseEnumClockAccuracy 175 }

ieee1588BaseEnumCaAltPtpProfile176 OBJECT-IDENTITY
    STATUS       current
    DESCRIPTION
        "ClockAccuracy 0xB0: Designated for assignment by alternate PTP
        Profiles"
    REFERENCE    "IEEE 1588-2019: clause 7.6.2.6"
    ::= { ieee1588BaseEnumClockAccuracy 176 }

ieee1588BaseEnumCaAltPtpProfile177 OBJECT-IDENTITY
    STATUS       current
    DESCRIPTION
        "ClockAccuracy 0xB1: Designated for assignment by alternate PTP
        Profiles"
    REFERENCE    "IEEE 1588-2019: clause 7.6.2.6"
    ::= { ieee1588BaseEnumClockAccuracy 177 }

ieee1588BaseEnumCaAltPtpProfile178 OBJECT-IDENTITY
    STATUS       current
    DESCRIPTION
        "ClockAccuracy 0xB2: Designated for assignment by alternate PTP
        Profiles"
    REFERENCE    "IEEE 1588-2019: clause 7.6.2.6"
    ::= { ieee1588BaseEnumClockAccuracy 178 }

ieee1588BaseEnumCaAltPtpProfile179 OBJECT-IDENTITY
    STATUS       current
    DESCRIPTION
        "ClockAccuracy 0xB3: Designated for assignment by alternate PTP
        Profiles"
    REFERENCE    "IEEE 1588-2019: clause 7.6.2.6"
    ::= { ieee1588BaseEnumClockAccuracy 179 }

ieee1588BaseEnumCaAltPtpProfile180 OBJECT-IDENTITY
    STATUS       current
    DESCRIPTION
        "ClockAccuracy 0xB4: Designated for assignment by alternate PTP
        Profiles"
    REFERENCE    "IEEE 1588-2019: clause 7.6.2.6"
    ::= { ieee1588BaseEnumClockAccuracy 180 }

ieee1588BaseEnumCaAltPtpProfile181 OBJECT-IDENTITY
    STATUS       current
    DESCRIPTION
        "ClockAccuracy 0xB5: Designated for assignment by alternate PTP
        Profiles"
    REFERENCE    "IEEE 1588-2019: clause 7.6.2.6"
    ::= { ieee1588BaseEnumClockAccuracy 181 }

ieee1588BaseEnumCaAltPtpProfile182 OBJECT-IDENTITY
    STATUS       current
    DESCRIPTION
        "ClockAccuracy 0xB6: Designated for assignment by alternate PTP
        Profiles"
    REFERENCE    "IEEE 1588-2019: clause 7.6.2.6"
    ::= { ieee1588BaseEnumClockAccuracy 182 }

ieee1588BaseEnumCaAltPtpProfile183 OBJECT-IDENTITY
    STATUS       current
    DESCRIPTION
        "ClockAccuracy 0xB7: Designated for assignment by alternate PTP
        Profiles"
    REFERENCE    "IEEE 1588-2019: clause 7.6.2.6"
    ::= { ieee1588BaseEnumClockAccuracy 183 }

ieee1588BaseEnumCaAltPtpProfile184 OBJECT-IDENTITY
    STATUS       current
    DESCRIPTION
        "ClockAccuracy 0xB8: Designated for assignment by alternate PTP
        Profiles"
    REFERENCE    "IEEE 1588-2019: clause 7.6.2.6"
    ::= { ieee1588BaseEnumClockAccuracy 184 }

ieee1588BaseEnumCaAltPtpProfile185 OBJECT-IDENTITY
    STATUS       current
    DESCRIPTION
        "ClockAccuracy 0xB9: Designated for assignment by alternate PTP
        Profiles"
    REFERENCE    "IEEE 1588-2019: clause 7.6.2.6"
    ::= { ieee1588BaseEnumClockAccuracy 185 }

ieee1588BaseEnumCaAltPtpProfile186 OBJECT-IDENTITY
    STATUS       current
    DESCRIPTION
        "ClockAccuracy 0xBA: Designated for assignment by alternate PTP
        Profiles"
    REFERENCE    "IEEE 1588-2019: clause 7.6.2.6"
    ::= { ieee1588BaseEnumClockAccuracy 186 }

ieee1588BaseEnumCaAltPtpProfile187 OBJECT-IDENTITY
    STATUS       current
    DESCRIPTION
        "ClockAccuracy 0xBB: Designated for assignment by alternate PTP
        Profiles"
    REFERENCE    "IEEE 1588-2019: clause 7.6.2.6"
    ::= { ieee1588BaseEnumClockAccuracy 187 }

ieee1588BaseEnumCaAltPtpProfile188 OBJECT-IDENTITY
    STATUS       current
    DESCRIPTION
        "ClockAccuracy 0xBC: Designated for assignment by alternate PTP
        Profiles"
    REFERENCE    "IEEE 1588-2019: clause 7.6.2.6"
    ::= { ieee1588BaseEnumClockAccuracy 188 }

ieee1588BaseEnumCaAltPtpProfile189 OBJECT-IDENTITY
    STATUS       current
    DESCRIPTION
        "ClockAccuracy 0xBD: Designated for assignment by alternate PTP
        Profiles"
    REFERENCE    "IEEE 1588-2019: clause 7.6.2.6"
    ::= { ieee1588BaseEnumClockAccuracy 189 }

ieee1588BaseEnumCaAltPtpProfile190 OBJECT-IDENTITY
    STATUS       current
    DESCRIPTION
        "ClockAccuracy 0xBE: Designated for assignment by alternate PTP
        Profiles"
    REFERENCE    "IEEE 1588-2019: clause 7.6.2.6"
    ::= { ieee1588BaseEnumClockAccuracy 190 }

ieee1588BaseEnumCaAltPtpProfile191 OBJECT-IDENTITY
    STATUS       current
    DESCRIPTION
        "ClockAccuracy 0xBF: Designated for assignment by alternate PTP
        Profiles"
    REFERENCE    "IEEE 1588-2019: clause 7.6.2.6"
    ::= { ieee1588BaseEnumClockAccuracy 191 }

ieee1588BaseEnumCaAltPtpProfile192 OBJECT-IDENTITY
    STATUS       current
    DESCRIPTION
        "ClockAccuracy 0xC0: Designated for assignment by alternate PTP
        Profiles"
    REFERENCE    "IEEE 1588-2019: clause 7.6.2.6"
    ::= { ieee1588BaseEnumClockAccuracy 192 }

ieee1588BaseEnumCaAltPtpProfile193 OBJECT-IDENTITY
    STATUS       current
    DESCRIPTION
        "ClockAccuracy 0xC1: Designated for assignment by alternate PTP
        Profiles"
    REFERENCE    "IEEE 1588-2019: clause 7.6.2.6"
    ::= { ieee1588BaseEnumClockAccuracy 193 }

ieee1588BaseEnumCaAltPtpProfile194 OBJECT-IDENTITY
    STATUS       current
    DESCRIPTION
        "ClockAccuracy 0xC2: Designated for assignment by alternate PTP
        Profiles"
    REFERENCE    "IEEE 1588-2019: clause 7.6.2.6"
    ::= { ieee1588BaseEnumClockAccuracy 194 }

ieee1588BaseEnumCaAltPtpProfile195 OBJECT-IDENTITY
    STATUS       current
    DESCRIPTION
        "ClockAccuracy 0xC3: Designated for assignment by alternate PTP
        Profiles"
    REFERENCE    "IEEE 1588-2019: clause 7.6.2.6"
    ::= { ieee1588BaseEnumClockAccuracy 195 }

ieee1588BaseEnumCaAltPtpProfile196 OBJECT-IDENTITY
    STATUS       current
    DESCRIPTION
        "ClockAccuracy 0xC4: Designated for assignment by alternate PTP
        Profiles"
    REFERENCE    "IEEE 1588-2019: clause 7.6.2.6"
    ::= { ieee1588BaseEnumClockAccuracy 196 }

ieee1588BaseEnumCaAltPtpProfile197 OBJECT-IDENTITY
    STATUS       current
    DESCRIPTION
        "ClockAccuracy 0xC5: Designated for assignment by alternate PTP
        Profiles"
    REFERENCE    "IEEE 1588-2019: clause 7.6.2.6"
    ::= { ieee1588BaseEnumClockAccuracy 197 }

ieee1588BaseEnumCaAltPtpProfile198 OBJECT-IDENTITY
    STATUS       current
    DESCRIPTION
        "ClockAccuracy 0xC6: Designated for assignment by alternate PTP
        Profiles"
    REFERENCE    "IEEE 1588-2019: clause 7.6.2.6"
    ::= { ieee1588BaseEnumClockAccuracy 198 }

ieee1588BaseEnumCaAltPtpProfile199 OBJECT-IDENTITY
    STATUS       current
    DESCRIPTION
        "ClockAccuracy 0xC7: Designated for assignment by alternate PTP
        Profiles"
    REFERENCE    "IEEE 1588-2019: clause 7.6.2.6"
    ::= { ieee1588BaseEnumClockAccuracy 199 }

ieee1588BaseEnumCaAltPtpProfile200 OBJECT-IDENTITY
    STATUS       current
    DESCRIPTION
        "ClockAccuracy 0xC8: Designated for assignment by alternate PTP
        Profiles"
    REFERENCE    "IEEE 1588-2019: clause 7.6.2.6"
    ::= { ieee1588BaseEnumClockAccuracy 200 }

ieee1588BaseEnumCaAltPtpProfile201 OBJECT-IDENTITY
    STATUS       current
    DESCRIPTION
        "ClockAccuracy 0xC9: Designated for assignment by alternate PTP
        Profiles"
    REFERENCE    "IEEE 1588-2019: clause 7.6.2.6"
    ::= { ieee1588BaseEnumClockAccuracy 201 }

ieee1588BaseEnumCaAltPtpProfile202 OBJECT-IDENTITY
    STATUS       current
    DESCRIPTION
        "ClockAccuracy 0xCA: Designated for assignment by alternate PTP
        Profiles"
    REFERENCE    "IEEE 1588-2019: clause 7.6.2.6"
    ::= { ieee1588BaseEnumClockAccuracy 202 }

ieee1588BaseEnumCaAltPtpProfile203 OBJECT-IDENTITY
    STATUS       current
    DESCRIPTION
        "ClockAccuracy 0xCB: Designated for assignment by alternate PTP
        Profiles"
    REFERENCE    "IEEE 1588-2019: clause 7.6.2.6"
    ::= { ieee1588BaseEnumClockAccuracy 203 }

ieee1588BaseEnumCaAltPtpProfile204 OBJECT-IDENTITY
    STATUS       current
    DESCRIPTION
        "ClockAccuracy 0xCC: Designated for assignment by alternate PTP
        Profiles"
    REFERENCE    "IEEE 1588-2019: clause 7.6.2.6"
    ::= { ieee1588BaseEnumClockAccuracy 204 }

ieee1588BaseEnumCaAltPtpProfile205 OBJECT-IDENTITY
    STATUS       current
    DESCRIPTION
        "ClockAccuracy 0xCD: Designated for assignment by alternate PTP
        Profiles"
    REFERENCE    "IEEE 1588-2019: clause 7.6.2.6"
    ::= { ieee1588BaseEnumClockAccuracy 205 }

ieee1588BaseEnumCaAltPtpProfile206 OBJECT-IDENTITY
    STATUS       current
    DESCRIPTION
        "ClockAccuracy 0xCE: Designated for assignment by alternate PTP
        Profiles"
    REFERENCE    "IEEE 1588-2019: clause 7.6.2.6"
    ::= { ieee1588BaseEnumClockAccuracy 206 }

ieee1588BaseEnumCaAltPtpProfile207 OBJECT-IDENTITY
    STATUS       current
    DESCRIPTION
        "ClockAccuracy 0xCF: Designated for assignment by alternate PTP
        Profiles"
    REFERENCE    "IEEE 1588-2019: clause 7.6.2.6"
    ::= { ieee1588BaseEnumClockAccuracy 207 }

ieee1588BaseEnumCaAltPtpProfile208 OBJECT-IDENTITY
    STATUS       current
    DESCRIPTION
        "ClockAccuracy 0xD0: Designated for assignment by alternate PTP
        Profiles"
    REFERENCE    "IEEE 1588-2019: clause 7.6.2.6"
    ::= { ieee1588BaseEnumClockAccuracy 208 }

ieee1588BaseEnumCaAltPtpProfile209 OBJECT-IDENTITY
    STATUS       current
    DESCRIPTION
        "ClockAccuracy 0xD1: Designated for assignment by alternate PTP
        Profiles"
    REFERENCE    "IEEE 1588-2019: clause 7.6.2.6"
    ::= { ieee1588BaseEnumClockAccuracy 209 }

ieee1588BaseEnumCaAltPtpProfile210 OBJECT-IDENTITY
    STATUS       current
    DESCRIPTION
        "ClockAccuracy 0xD2: Designated for assignment by alternate PTP
        Profiles"
    REFERENCE    "IEEE 1588-2019: clause 7.6.2.6"
    ::= { ieee1588BaseEnumClockAccuracy 210 }

ieee1588BaseEnumCaAltPtpProfile211 OBJECT-IDENTITY
    STATUS       current
    DESCRIPTION
        "ClockAccuracy 0xD3: Designated for assignment by alternate PTP
        Profiles"
    REFERENCE    "IEEE 1588-2019: clause 7.6.2.6"
    ::= { ieee1588BaseEnumClockAccuracy 211 }

ieee1588BaseEnumCaAltPtpProfile212 OBJECT-IDENTITY
    STATUS       current
    DESCRIPTION
        "ClockAccuracy 0xD4: Designated for assignment by alternate PTP
        Profiles"
    REFERENCE    "IEEE 1588-2019: clause 7.6.2.6"
    ::= { ieee1588BaseEnumClockAccuracy 212 }

ieee1588BaseEnumCaAltPtpProfile213 OBJECT-IDENTITY
    STATUS       current
    DESCRIPTION
        "ClockAccuracy 0xD5: Designated for assignment by alternate PTP
        Profiles"
    REFERENCE    "IEEE 1588-2019: clause 7.6.2.6"
    ::= { ieee1588BaseEnumClockAccuracy 213 }

ieee1588BaseEnumCaAltPtpProfile214 OBJECT-IDENTITY
    STATUS       current
    DESCRIPTION
        "ClockAccuracy 0xD6: Designated for assignment by alternate PTP
        Profiles"
    REFERENCE    "IEEE 1588-2019: clause 7.6.2.6"
    ::= { ieee1588BaseEnumClockAccuracy 214 }

ieee1588BaseEnumCaAltPtpProfile215 OBJECT-IDENTITY
    STATUS       current
    DESCRIPTION
        "ClockAccuracy 0xD7: Designated for assignment by alternate PTP
        Profiles"
    REFERENCE    "IEEE 1588-2019: clause 7.6.2.6"
    ::= { ieee1588BaseEnumClockAccuracy 215 }

ieee1588BaseEnumCaAltPtpProfile216 OBJECT-IDENTITY
    STATUS       current
    DESCRIPTION
        "ClockAccuracy 0xD8: Designated for assignment by alternate PTP
        Profiles"
    REFERENCE    "IEEE 1588-2019: clause 7.6.2.6"
    ::= { ieee1588BaseEnumClockAccuracy 216 }

ieee1588BaseEnumCaAltPtpProfile217 OBJECT-IDENTITY
    STATUS       current
    DESCRIPTION
        "ClockAccuracy 0xD9: Designated for assignment by alternate PTP
        Profiles"
    REFERENCE    "IEEE 1588-2019: clause 7.6.2.6"
    ::= { ieee1588BaseEnumClockAccuracy 217 }

ieee1588BaseEnumCaAltPtpProfile218 OBJECT-IDENTITY
    STATUS       current
    DESCRIPTION
        "ClockAccuracy 0xDA: Designated for assignment by alternate PTP
        Profiles"
    REFERENCE    "IEEE 1588-2019: clause 7.6.2.6"
    ::= { ieee1588BaseEnumClockAccuracy 218 }

ieee1588BaseEnumCaAltPtpProfile219 OBJECT-IDENTITY
    STATUS       current
    DESCRIPTION
        "ClockAccuracy 0xDB: Designated for assignment by alternate PTP
        Profiles"
    REFERENCE    "IEEE 1588-2019: clause 7.6.2.6"
    ::= { ieee1588BaseEnumClockAccuracy 219 }

ieee1588BaseEnumCaAltPtpProfile220 OBJECT-IDENTITY
    STATUS       current
    DESCRIPTION
        "ClockAccuracy 0xDC: Designated for assignment by alternate PTP
        Profiles"
    REFERENCE    "IEEE 1588-2019: clause 7.6.2.6"
    ::= { ieee1588BaseEnumClockAccuracy 220 }

ieee1588BaseEnumCaAltPtpProfile221 OBJECT-IDENTITY
    STATUS       current
    DESCRIPTION
        "ClockAccuracy 0xDD: Designated for assignment by alternate PTP
        Profiles"
    REFERENCE    "IEEE 1588-2019: clause 7.6.2.6"
    ::= { ieee1588BaseEnumClockAccuracy 221 }

ieee1588BaseEnumCaAltPtpProfile222 OBJECT-IDENTITY
    STATUS       current
    DESCRIPTION
        "ClockAccuracy 0xDE: Designated for assignment by alternate PTP
        Profiles"
    REFERENCE    "IEEE 1588-2019: clause 7.6.2.6"
    ::= { ieee1588BaseEnumClockAccuracy 222 }

ieee1588BaseEnumCaAltPtpProfile223 OBJECT-IDENTITY
    STATUS       current
    DESCRIPTION
        "ClockAccuracy 0xDF: Designated for assignment by alternate PTP
        Profiles"
    REFERENCE    "IEEE 1588-2019: clause 7.6.2.6"
    ::= { ieee1588BaseEnumClockAccuracy 223 }

ieee1588BaseEnumCaAltPtpProfile224 OBJECT-IDENTITY
    STATUS       current
    DESCRIPTION
        "ClockAccuracy 0xE0: Designated for assignment by alternate PTP
        Profiles"
    REFERENCE    "IEEE 1588-2019: clause 7.6.2.6"
    ::= { ieee1588BaseEnumClockAccuracy 224 }

ieee1588BaseEnumCaAltPtpProfile225 OBJECT-IDENTITY
    STATUS       current
    DESCRIPTION
        "ClockAccuracy 0xE1: Designated for assignment by alternate PTP
        Profiles"
    REFERENCE    "IEEE 1588-2019: clause 7.6.2.6"
    ::= { ieee1588BaseEnumClockAccuracy 225 }

ieee1588BaseEnumCaAltPtpProfile226 OBJECT-IDENTITY
    STATUS       current
    DESCRIPTION
        "ClockAccuracy 0xE2: Designated for assignment by alternate PTP
        Profiles"
    REFERENCE    "IEEE 1588-2019: clause 7.6.2.6"
    ::= { ieee1588BaseEnumClockAccuracy 226 }

ieee1588BaseEnumCaAltPtpProfile227 OBJECT-IDENTITY
    STATUS       current
    DESCRIPTION
        "ClockAccuracy 0xE3: Designated for assignment by alternate PTP
        Profiles"
    REFERENCE    "IEEE 1588-2019: clause 7.6.2.6"
    ::= { ieee1588BaseEnumClockAccuracy 227 }

ieee1588BaseEnumCaAltPtpProfile228 OBJECT-IDENTITY
    STATUS       current
    DESCRIPTION
        "ClockAccuracy 0xE4: Designated for assignment by alternate PTP
        Profiles"
    REFERENCE    "IEEE 1588-2019: clause 7.6.2.6"
    ::= { ieee1588BaseEnumClockAccuracy 228 }

ieee1588BaseEnumCaAltPtpProfile229 OBJECT-IDENTITY
    STATUS       current
    DESCRIPTION
        "ClockAccuracy 0xE5: Designated for assignment by alternate PTP
        Profiles"
    REFERENCE    "IEEE 1588-2019: clause 7.6.2.6"
    ::= { ieee1588BaseEnumClockAccuracy 229 }

ieee1588BaseEnumCaAltPtpProfile230 OBJECT-IDENTITY
    STATUS       current
    DESCRIPTION
        "ClockAccuracy 0xE6: Designated for assignment by alternate PTP
        Profiles"
    REFERENCE    "IEEE 1588-2019: clause 7.6.2.6"
    ::= { ieee1588BaseEnumClockAccuracy 230 }

ieee1588BaseEnumCaAltPtpProfile231 OBJECT-IDENTITY
    STATUS       current
    DESCRIPTION
        "ClockAccuracy 0xE7: Designated for assignment by alternate PTP
        Profiles"
    REFERENCE    "IEEE 1588-2019: clause 7.6.2.6"
    ::= { ieee1588BaseEnumClockAccuracy 231 }

ieee1588BaseEnumCaAltPtpProfile232 OBJECT-IDENTITY
    STATUS       current
    DESCRIPTION
        "ClockAccuracy 0xE8: Designated for assignment by alternate PTP
        Profiles"
    REFERENCE    "IEEE 1588-2019: clause 7.6.2.6"
    ::= { ieee1588BaseEnumClockAccuracy 232 }

ieee1588BaseEnumCaAltPtpProfile233 OBJECT-IDENTITY
    STATUS       current
    DESCRIPTION
        "ClockAccuracy 0xE9: Designated for assignment by alternate PTP
        Profiles"
    REFERENCE    "IEEE 1588-2019: clause 7.6.2.6"
    ::= { ieee1588BaseEnumClockAccuracy 233 }

ieee1588BaseEnumCaAltPtpProfile234 OBJECT-IDENTITY
    STATUS       current
    DESCRIPTION
        "ClockAccuracy 0xEA: Designated for assignment by alternate PTP
        Profiles"
    REFERENCE    "IEEE 1588-2019: clause 7.6.2.6"
    ::= { ieee1588BaseEnumClockAccuracy 234 }

ieee1588BaseEnumCaAltPtpProfile235 OBJECT-IDENTITY
    STATUS       current
    DESCRIPTION
        "ClockAccuracy 0xEB: Designated for assignment by alternate PTP
        Profiles"
    REFERENCE    "IEEE 1588-2019: clause 7.6.2.6"
    ::= { ieee1588BaseEnumClockAccuracy 235 }

ieee1588BaseEnumCaAltPtpProfile236 OBJECT-IDENTITY
    STATUS       current
    DESCRIPTION
        "ClockAccuracy 0xEC: Designated for assignment by alternate PTP
        Profiles"
    REFERENCE    "IEEE 1588-2019: clause 7.6.2.6"
    ::= { ieee1588BaseEnumClockAccuracy 236 }

ieee1588BaseEnumCaAltPtpProfile237 OBJECT-IDENTITY
    STATUS       current
    DESCRIPTION
        "ClockAccuracy 0xED: Designated for assignment by alternate PTP
        Profiles"
    REFERENCE    "IEEE 1588-2019: clause 7.6.2.6"
    ::= { ieee1588BaseEnumClockAccuracy 237 }

ieee1588BaseEnumCaAltPtpProfile238 OBJECT-IDENTITY
    STATUS       current
    DESCRIPTION
        "ClockAccuracy 0xEE: Designated for assignment by alternate PTP
        Profiles"
    REFERENCE    "IEEE 1588-2019: clause 7.6.2.6"
    ::= { ieee1588BaseEnumClockAccuracy 238 }

ieee1588BaseEnumCaAltPtpProfile239 OBJECT-IDENTITY
    STATUS       current
    DESCRIPTION
        "ClockAccuracy 0xEF: Designated for assignment by alternate PTP
        Profiles"
    REFERENCE    "IEEE 1588-2019: clause 7.6.2.6"
    ::= { ieee1588BaseEnumClockAccuracy 239 }

ieee1588BaseEnumCaAltPtpProfile240 OBJECT-IDENTITY
    STATUS       current
    DESCRIPTION
        "ClockAccuracy 0xF0: Designated for assignment by alternate PTP
        Profiles"
    REFERENCE    "IEEE 1588-2019: clause 7.6.2.6"
    ::= { ieee1588BaseEnumClockAccuracy 240 }

ieee1588BaseEnumCaAltPtpProfile241 OBJECT-IDENTITY
    STATUS       current
    DESCRIPTION
        "ClockAccuracy 0xF1: Designated for assignment by alternate PTP
        Profiles"
    REFERENCE    "IEEE 1588-2019: clause 7.6.2.6"
    ::= { ieee1588BaseEnumClockAccuracy 241 }

ieee1588BaseEnumCaAltPtpProfile242 OBJECT-IDENTITY
    STATUS       current
    DESCRIPTION
        "ClockAccuracy 0xF2: Designated for assignment by alternate PTP
        Profiles"
    REFERENCE    "IEEE 1588-2019: clause 7.6.2.6"
    ::= { ieee1588BaseEnumClockAccuracy 242 }

ieee1588BaseEnumCaAltPtpProfile243 OBJECT-IDENTITY
    STATUS       current
    DESCRIPTION
        "ClockAccuracy 0xF3: Designated for assignment by alternate PTP
        Profiles"
    REFERENCE    "IEEE 1588-2019: clause 7.6.2.6"
    ::= { ieee1588BaseEnumClockAccuracy 243 }

ieee1588BaseEnumCaAltPtpProfile244 OBJECT-IDENTITY
    STATUS       current
    DESCRIPTION
        "ClockAccuracy 0xF4: Designated for assignment by alternate PTP
        Profiles"
    REFERENCE    "IEEE 1588-2019: clause 7.6.2.6"
    ::= { ieee1588BaseEnumClockAccuracy 244 }

ieee1588BaseEnumCaAltPtpProfile245 OBJECT-IDENTITY
    STATUS       current
    DESCRIPTION
        "ClockAccuracy 0xF5: Designated for assignment by alternate PTP
        Profiles"
    REFERENCE    "IEEE 1588-2019: clause 7.6.2.6"
    ::= { ieee1588BaseEnumClockAccuracy 245 }

ieee1588BaseEnumCaAltPtpProfile246 OBJECT-IDENTITY
    STATUS       current
    DESCRIPTION
        "ClockAccuracy 0xF6: Designated for assignment by alternate PTP
        Profiles"
    REFERENCE    "IEEE 1588-2019: clause 7.6.2.6"
    ::= { ieee1588BaseEnumClockAccuracy 246 }

ieee1588BaseEnumCaAltPtpProfile247 OBJECT-IDENTITY
    STATUS       current
    DESCRIPTION
        "ClockAccuracy 0xF7: Designated for assignment by alternate PTP
        Profiles"
    REFERENCE    "IEEE 1588-2019: clause 7.6.2.6"
    ::= { ieee1588BaseEnumClockAccuracy 247 }

ieee1588BaseEnumCaAltPtpProfile248 OBJECT-IDENTITY
    STATUS       current
    DESCRIPTION
        "ClockAccuracy 0xF8: Designated for assignment by alternate PTP
        Profiles"
    REFERENCE    "IEEE 1588-2019: clause 7.6.2.6"
    ::= { ieee1588BaseEnumClockAccuracy 248 }

ieee1588BaseEnumCaAltPtpProfile249 OBJECT-IDENTITY
    STATUS       current
    DESCRIPTION
        "ClockAccuracy 0xF9: Designated for assignment by alternate PTP
        Profiles"
    REFERENCE    "IEEE 1588-2019: clause 7.6.2.6"
    ::= { ieee1588BaseEnumClockAccuracy 249 }

ieee1588BaseEnumCaAltPtpProfile250 OBJECT-IDENTITY
    STATUS       current
    DESCRIPTION
        "ClockAccuracy 0xFA: Designated for assignment by alternate PTP
        Profiles"
    REFERENCE    "IEEE 1588-2019: clause 7.6.2.6"
    ::= { ieee1588BaseEnumClockAccuracy 250 }

ieee1588BaseEnumCaAltPtpProfile251 OBJECT-IDENTITY
    STATUS       current
    DESCRIPTION
        "ClockAccuracy 0xFB: Designated for assignment by alternate PTP
        Profiles"
    REFERENCE    "IEEE 1588-2019: clause 7.6.2.6"
    ::= { ieee1588BaseEnumClockAccuracy 251 }

ieee1588BaseEnumCaAltPtpProfile252 OBJECT-IDENTITY
    STATUS       current
    DESCRIPTION
        "ClockAccuracy 0xFC: Designated for assignment by alternate PTP
        Profiles"
    REFERENCE    "IEEE 1588-2019: clause 7.6.2.6"
    ::= { ieee1588BaseEnumClockAccuracy 252 }

ieee1588BaseEnumCaAltPtpProfile253 OBJECT-IDENTITY
    STATUS       current
    DESCRIPTION
        "ClockAccuracy 0xFD: Designated for assignment by alternate PTP
        Profiles"
    REFERENCE    "IEEE 1588-2019: clause 7.6.2.6"
    ::= { ieee1588BaseEnumClockAccuracy 253 }

ieee1588BaseEnumCaTimeAccurateToUnknown OBJECT-IDENTITY
    STATUS       current
    DESCRIPTION
        "ClockAccuracy 0xFE: Default value indicating unknown time
        accuracy."
    REFERENCE    "IEEE 1588-2019: clause 7.6.2.6"
    ::= { ieee1588BaseEnumClockAccuracy 254 }

-- Group contains enumeration of Clock Class values from IEEE Std
-- 1588-2019 7.6.2.5, with values defined in this group. Unused ranges
-- of values:
-- 0 - Reserved for assignment by the IEEE 1588 Working Group to enable
--     compatibility with future versions.
-- 1..5 - Reserved
-- 8 - Reserved
-- 9..10 - Reserved for assignment by the IEEE 1588 Working Group, to
--         enable compatibility with future versions.
-- 11..12 - Reserved
-- 15..51 - Reserved
-- 53..57 - Reserved
-- 59..67 - Reserved
-- 123..132 - Reserved
-- 171..186 - Reserved
-- 188..192 - Reserved
-- 194..215 - Reserved
-- 233..247 - Reserved
-- 249..254 – Reserved
ieee1588BaseEnumClockClass OBJECT IDENTIFIER ::= { ieee1588BaseEnum 2 }

ieee1588BaseEnumCcPrimarySync OBJECT-IDENTITY
    STATUS       current
    DESCRIPTION
        "ClockClass 6: A PTP Instance that is synchronized to a primary
        reference time source. The timescale distributed shall be PTP."
    REFERENCE    "IEEE 1588-2019: clause 7.6.2.5"
    ::= { ieee1588BaseEnumClockClass 6 }

ieee1588BaseEnumCcPrimaryHoldover OBJECT-IDENTITY
    STATUS       current
    DESCRIPTION
        "ClockClass 7: A PTP Instance that has previously been
        designated as clockClass 6, but that has lost the ability to
        synchronize to a primary reference time source and is in
        holdover mode and within holdover specifications. Or a PTP
        Instance designated with clockClass 7 based on the Holdover
        upgrade option. The timescale distributed shall be PTP."
    REFERENCE    "IEEE 1588-2019: clause 7.6.2.5"
    ::= { ieee1588BaseEnumClockClass 7 }

ieee1588BaseEnumCcApplicationSpecificSync OBJECT-IDENTITY
    STATUS       current
    DESCRIPTION
        "ClockClass 13: A PTP Instance that is synchronized to an
        application-specific source of time. The timescale distributed
        shall be ARB."
    REFERENCE    "IEEE 1588-2019: clause 7.6.2.5"
    ::= { ieee1588BaseEnumClockClass 13 }

ieee1588BaseEnumCcApplicationSpecficHoldover OBJECT-IDENTITY
    STATUS       current
    DESCRIPTION
        "ClockClass 14: A PTP Instance that has previously been
        designated as clockClass 13, but that has lost the ability to
        synchronize to an application-specific source of time and is in
        holdover mode and within holdover specifications. Or a PTP
        Instance designated with clockClass 14 based on the Holdover
        upgrade option. The timescale distributed shall be ARB."
    REFERENCE    "IEEE 1588-2019: clause 7.6.2.5"
    ::= { ieee1588BaseEnumClockClass 14 }

ieee1588BaseEnumCcPrimaryHoldoverDegradationA OBJECT-IDENTITY
    STATUS       current
    DESCRIPTION
        "ClockClass 52: Degradation alternative A for a PTP Instance of
        clockClass 7 that is not within holdover specification or that
        is based on the specifications of the Holdover upgrade option."
    REFERENCE    "IEEE 1588-2019: clause 7.6.2.5"
    ::= { ieee1588BaseEnumClockClass 52 }

ieee1588BaseEnumCcApplicationSpecificHoldoverDegradationA
                                                         OBJECT-IDENTITY
    STATUS       current
    DESCRIPTION
        "ClockClass 58: Degradation alternative A for a PTP Instance of
        clockClass 14 that is not within holdover specification or that
        is based on the specifications of the Holdover upgrade option."
    REFERENCE    "IEEE 1588-2019: clause 7.6.2.5"
    ::= { ieee1588BaseEnumClockClass 58 }

ieee1588BaseEnumCcAltPtpProfile68 OBJECT-IDENTITY
    STATUS       current
    DESCRIPTION
        "ClockClass 68: For use by alternate PTP Profiles"
    REFERENCE    "IEEE 1588-2019: clause 7.6.2.5"
    ::= { ieee1588BaseEnumClockClass 68 }

ieee1588BaseEnumCcAltPtpProfile69 OBJECT-IDENTITY
    STATUS       current
    DESCRIPTION
        "ClockClass 69: For use by alternate PTP Profiles"
    REFERENCE    "IEEE 1588-2019: clause 7.6.2.5"
    ::= { ieee1588BaseEnumClockClass 69 }

ieee1588BaseEnumCcAltPtpProfile70 OBJECT-IDENTITY
    STATUS       current
    DESCRIPTION
        "ClockClass 70: For use by alternate PTP Profiles"
    REFERENCE    "IEEE 1588-2019: clause 7.6.2.5"
    ::= { ieee1588BaseEnumClockClass 70 }

ieee1588BaseEnumCcAltPtpProfile71 OBJECT-IDENTITY
    STATUS       current
    DESCRIPTION
        "ClockClass 71: For use by alternate PTP Profiles"
    REFERENCE    "IEEE 1588-2019: clause 7.6.2.5"
    ::= { ieee1588BaseEnumClockClass 71 }

ieee1588BaseEnumCcAltPtpProfile72 OBJECT-IDENTITY
    STATUS       current
    DESCRIPTION
        "ClockClass 72: For use by alternate PTP Profiles"
    REFERENCE    "IEEE 1588-2019: clause 7.6.2.5"
    ::= { ieee1588BaseEnumClockClass 72 }

ieee1588BaseEnumCcAltPtpProfile73 OBJECT-IDENTITY
    STATUS       current
    DESCRIPTION
        "ClockClass 73: For use by alternate PTP Profiles"
    REFERENCE    "IEEE 1588-2019: clause 7.6.2.5"
    ::= { ieee1588BaseEnumClockClass 73 }

ieee1588BaseEnumCcAltPtpProfile74 OBJECT-IDENTITY
    STATUS       current
    DESCRIPTION
        "ClockClass 74: For use by alternate PTP Profiles"
    REFERENCE    "IEEE 1588-2019: clause 7.6.2.5"
    ::= { ieee1588BaseEnumClockClass 74 }

ieee1588BaseEnumCcAltPtpProfile75 OBJECT-IDENTITY
    STATUS       current
    DESCRIPTION
        "ClockClass 75: For use by alternate PTP Profiles"
    REFERENCE    "IEEE 1588-2019: clause 7.6.2.5"
    ::= { ieee1588BaseEnumClockClass 75 }

ieee1588BaseEnumCcAltPtpProfile76 OBJECT-IDENTITY
    STATUS       current
    DESCRIPTION
        "ClockClass 76: For use by alternate PTP Profiles"
    REFERENCE    "IEEE 1588-2019: clause 7.6.2.5"
    ::= { ieee1588BaseEnumClockClass 76 }

ieee1588BaseEnumCcAltPtpProfile77 OBJECT-IDENTITY
    STATUS       current
    DESCRIPTION
        "ClockClass 77: For use by alternate PTP Profiles"
    REFERENCE    "IEEE 1588-2019: clause 7.6.2.5"
    ::= { ieee1588BaseEnumClockClass 77 }

ieee1588BaseEnumCcAltPtpProfile78 OBJECT-IDENTITY
    STATUS       current
    DESCRIPTION
        "ClockClass 78: For use by alternate PTP Profiles"
    REFERENCE    "IEEE 1588-2019: clause 7.6.2.5"
    ::= { ieee1588BaseEnumClockClass 78 }

ieee1588BaseEnumCcAltPtpProfile79 OBJECT-IDENTITY
    STATUS       current
    DESCRIPTION
        "ClockClass 79: For use by alternate PTP Profiles"
    REFERENCE    "IEEE 1588-2019: clause 7.6.2.5"
    ::= { ieee1588BaseEnumClockClass 79 }

ieee1588BaseEnumCcAltPtpProfile80 OBJECT-IDENTITY
    STATUS       current
    DESCRIPTION
        "ClockClass 80: For use by alternate PTP Profiles"
    REFERENCE    "IEEE 1588-2019: clause 7.6.2.5"
    ::= { ieee1588BaseEnumClockClass 80 }

ieee1588BaseEnumCcAltPtpProfile81 OBJECT-IDENTITY
    STATUS       current
    DESCRIPTION
        "ClockClass 81: For use by alternate PTP Profiles"
    REFERENCE    "IEEE 1588-2019: clause 7.6.2.5"
    ::= { ieee1588BaseEnumClockClass 81 }

ieee1588BaseEnumCcAltPtpProfile82 OBJECT-IDENTITY
    STATUS       current
    DESCRIPTION
        "ClockClass 82: For use by alternate PTP Profiles"
    REFERENCE    "IEEE 1588-2019: clause 7.6.2.5"
    ::= { ieee1588BaseEnumClockClass 82 }

ieee1588BaseEnumCcAltPtpProfile83 OBJECT-IDENTITY
    STATUS       current
    DESCRIPTION
        "ClockClass 83: For use by alternate PTP Profiles"
    REFERENCE    "IEEE 1588-2019: clause 7.6.2.5"
    ::= { ieee1588BaseEnumClockClass 83 }

ieee1588BaseEnumCcAltPtpProfile84 OBJECT-IDENTITY
    STATUS       current
    DESCRIPTION
        "ClockClass 84: For use by alternate PTP Profiles"
    REFERENCE    "IEEE 1588-2019: clause 7.6.2.5"
    ::= { ieee1588BaseEnumClockClass 84 }

ieee1588BaseEnumCcAltPtpProfile85 OBJECT-IDENTITY
    STATUS       current
    DESCRIPTION
        "ClockClass 85: For use by alternate PTP Profiles"
    REFERENCE    "IEEE 1588-2019: clause 7.6.2.5"
    ::= { ieee1588BaseEnumClockClass 85 }

ieee1588BaseEnumCcAltPtpProfile86 OBJECT-IDENTITY
    STATUS       current
    DESCRIPTION
        "ClockClass 86: For use by alternate PTP Profiles"
    REFERENCE    "IEEE 1588-2019: clause 7.6.2.5"
    ::= { ieee1588BaseEnumClockClass 86 }

ieee1588BaseEnumCcAltPtpProfile87 OBJECT-IDENTITY
    STATUS       current
    DESCRIPTION
        "ClockClass 87: For use by alternate PTP Profiles"
    REFERENCE    "IEEE 1588-2019: clause 7.6.2.5"
    ::= { ieee1588BaseEnumClockClass 87 }

ieee1588BaseEnumCcAltPtpProfile88 OBJECT-IDENTITY
    STATUS       current
    DESCRIPTION
        "ClockClass 88: For use by alternate PTP Profiles"
    REFERENCE    "IEEE 1588-2019: clause 7.6.2.5"
    ::= { ieee1588BaseEnumClockClass 88 }

ieee1588BaseEnumCcAltPtpProfile89 OBJECT-IDENTITY
    STATUS       current
    DESCRIPTION
        "ClockClass 89: For use by alternate PTP Profiles"
    REFERENCE    "IEEE 1588-2019: clause 7.6.2.5"
    ::= { ieee1588BaseEnumClockClass 89 }

ieee1588BaseEnumCcAltPtpProfile90 OBJECT-IDENTITY
    STATUS       current
    DESCRIPTION
        "ClockClass 90: For use by alternate PTP Profiles"
    REFERENCE    "IEEE 1588-2019: clause 7.6.2.5"
    ::= { ieee1588BaseEnumClockClass 90 }

ieee1588BaseEnumCcAltPtpProfile91 OBJECT-IDENTITY
    STATUS       current
    DESCRIPTION
        "ClockClass 91: For use by alternate PTP Profiles"
    REFERENCE    "IEEE 1588-2019: clause 7.6.2.5"
    ::= { ieee1588BaseEnumClockClass 91 }

ieee1588BaseEnumCcAltPtpProfile92 OBJECT-IDENTITY
    STATUS       current
    DESCRIPTION
        "ClockClass 92: For use by alternate PTP Profiles"
    REFERENCE    "IEEE 1588-2019: clause 7.6.2.5"
    ::= { ieee1588BaseEnumClockClass 92 }

ieee1588BaseEnumCcAltPtpProfile93 OBJECT-IDENTITY
    STATUS       current
    DESCRIPTION
        "ClockClass 93: For use by alternate PTP Profiles"
    REFERENCE    "IEEE 1588-2019: clause 7.6.2.5"
    ::= { ieee1588BaseEnumClockClass 93 }

ieee1588BaseEnumCcAltPtpProfile94 OBJECT-IDENTITY
    STATUS       current
    DESCRIPTION
        "ClockClass 94: For use by alternate PTP Profiles"
    REFERENCE    "IEEE 1588-2019: clause 7.6.2.5"
    ::= { ieee1588BaseEnumClockClass 94 }

ieee1588BaseEnumCcAltPtpProfile95 OBJECT-IDENTITY
    STATUS       current
    DESCRIPTION
        "ClockClass 95: For use by alternate PTP Profiles"
    REFERENCE    "IEEE 1588-2019: clause 7.6.2.5"
    ::= { ieee1588BaseEnumClockClass 95 }

ieee1588BaseEnumCcAltPtpProfile96 OBJECT-IDENTITY
    STATUS       current
    DESCRIPTION
        "ClockClass 96: For use by alternate PTP Profiles"
    REFERENCE    "IEEE 1588-2019: clause 7.6.2.5"
    ::= { ieee1588BaseEnumClockClass 96 }

ieee1588BaseEnumCcAltPtpProfile97 OBJECT-IDENTITY
    STATUS       current
    DESCRIPTION
        "ClockClass 97: For use by alternate PTP Profiles"
    REFERENCE    "IEEE 1588-2019: clause 7.6.2.5"
    ::= { ieee1588BaseEnumClockClass 97 }

ieee1588BaseEnumCcAltPtpProfile98 OBJECT-IDENTITY
    STATUS       current
    DESCRIPTION
        "ClockClass 98: For use by alternate PTP Profiles"
    REFERENCE    "IEEE 1588-2019: clause 7.6.2.5"
    ::= { ieee1588BaseEnumClockClass 98 }

ieee1588BaseEnumCcAltPtpProfile99 OBJECT-IDENTITY
    STATUS       current
    DESCRIPTION
        "ClockClass 99: For use by alternate PTP Profiles"
    REFERENCE    "IEEE 1588-2019: clause 7.6.2.5"
    ::= { ieee1588BaseEnumClockClass 99 }

ieee1588BaseEnumCcAltPtpProfile100 OBJECT-IDENTITY
    STATUS       current
    DESCRIPTION
        "ClockClass 100: For use by alternate PTP Profiles"
    REFERENCE    "IEEE 1588-2019: clause 7.6.2.5"
    ::= { ieee1588BaseEnumClockClass 100 }

ieee1588BaseEnumCcAltPtpProfile101 OBJECT-IDENTITY
    STATUS       current
    DESCRIPTION
        "ClockClass 101: For use by alternate PTP Profiles"
    REFERENCE    "IEEE 1588-2019: clause 7.6.2.5"
    ::= { ieee1588BaseEnumClockClass 101 }

ieee1588BaseEnumCcAltPtpProfile102 OBJECT-IDENTITY
    STATUS       current
    DESCRIPTION
        "ClockClass 102: For use by alternate PTP Profiles"
    REFERENCE    "IEEE 1588-2019: clause 7.6.2.5"
    ::= { ieee1588BaseEnumClockClass 102 }

ieee1588BaseEnumCcAltPtpProfile103 OBJECT-IDENTITY
    STATUS       current
    DESCRIPTION
        "ClockClass 103: For use by alternate PTP Profiles"
    REFERENCE    "IEEE 1588-2019: clause 7.6.2.5"
    ::= { ieee1588BaseEnumClockClass 103 }

ieee1588BaseEnumCcAltPtpProfile104 OBJECT-IDENTITY
    STATUS       current
    DESCRIPTION
        "ClockClass 104: For use by alternate PTP Profiles"
    REFERENCE    "IEEE 1588-2019: clause 7.6.2.5"
    ::= { ieee1588BaseEnumClockClass 104 }

ieee1588BaseEnumCcAltPtpProfile105 OBJECT-IDENTITY
    STATUS       current
    DESCRIPTION
        "ClockClass 105: For use by alternate PTP Profiles"
    REFERENCE    "IEEE 1588-2019: clause 7.6.2.5"
    ::= { ieee1588BaseEnumClockClass 105 }

ieee1588BaseEnumCcAltPtpProfile106 OBJECT-IDENTITY
    STATUS       current
    DESCRIPTION
        "ClockClass 106: For use by alternate PTP Profiles"
    REFERENCE    "IEEE 1588-2019: clause 7.6.2.5"
    ::= { ieee1588BaseEnumClockClass 106 }

ieee1588BaseEnumCcAltPtpProfile107 OBJECT-IDENTITY
    STATUS       current
    DESCRIPTION
        "ClockClass 107: For use by alternate PTP Profiles"
    REFERENCE    "IEEE 1588-2019: clause 7.6.2.5"
    ::= { ieee1588BaseEnumClockClass 107 }

ieee1588BaseEnumCcAltPtpProfile108 OBJECT-IDENTITY
    STATUS       current
    DESCRIPTION
        "ClockClass 108: For use by alternate PTP Profiles"
    REFERENCE    "IEEE 1588-2019: clause 7.6.2.5"
    ::= { ieee1588BaseEnumClockClass 108 }

ieee1588BaseEnumCcAltPtpProfile109 OBJECT-IDENTITY
    STATUS       current
    DESCRIPTION
        "ClockClass 109: For use by alternate PTP Profiles"
    REFERENCE    "IEEE 1588-2019: clause 7.6.2.5"
    ::= { ieee1588BaseEnumClockClass 109 }

ieee1588BaseEnumCcAltPtpProfile110 OBJECT-IDENTITY
    STATUS       current
    DESCRIPTION
        "ClockClass 110: For use by alternate PTP Profiles"
    REFERENCE    "IEEE 1588-2019: clause 7.6.2.5"
    ::= { ieee1588BaseEnumClockClass 110 }

ieee1588BaseEnumCcAltPtpProfile111 OBJECT-IDENTITY
    STATUS       current
    DESCRIPTION
        "ClockClass 111: For use by alternate PTP Profiles"
    REFERENCE    "IEEE 1588-2019: clause 7.6.2.5"
    ::= { ieee1588BaseEnumClockClass 111 }

ieee1588BaseEnumCcAltPtpProfile112 OBJECT-IDENTITY
    STATUS       current
    DESCRIPTION
        "ClockClass 112: For use by alternate PTP Profiles"
    REFERENCE    "IEEE 1588-2019: clause 7.6.2.5"
    ::= { ieee1588BaseEnumClockClass 112 }

ieee1588BaseEnumCcAltPtpProfile113 OBJECT-IDENTITY
    STATUS       current
    DESCRIPTION
        "ClockClass 113: For use by alternate PTP Profiles"
    REFERENCE    "IEEE 1588-2019: clause 7.6.2.5"
    ::= { ieee1588BaseEnumClockClass 113 }

ieee1588BaseEnumCcAltPtpProfile114 OBJECT-IDENTITY
    STATUS       current
    DESCRIPTION
        "ClockClass 114: For use by alternate PTP Profiles"
    REFERENCE    "IEEE 1588-2019: clause 7.6.2.5"
    ::= { ieee1588BaseEnumClockClass 114 }

ieee1588BaseEnumCcAltPtpProfile115 OBJECT-IDENTITY
    STATUS       current
    DESCRIPTION
        "ClockClass 115: For use by alternate PTP Profiles"
    REFERENCE    "IEEE 1588-2019: clause 7.6.2.5"
    ::= { ieee1588BaseEnumClockClass 115 }

ieee1588BaseEnumCcAltPtpProfile116 OBJECT-IDENTITY
    STATUS       current
    DESCRIPTION
        "ClockClass 116: For use by alternate PTP Profiles"
    REFERENCE    "IEEE 1588-2019: clause 7.6.2.5"
    ::= { ieee1588BaseEnumClockClass 116 }

ieee1588BaseEnumCcAltPtpProfile117 OBJECT-IDENTITY
    STATUS       current
    DESCRIPTION
        "ClockClass 117: For use by alternate PTP Profiles"
    REFERENCE    "IEEE 1588-2019: clause 7.6.2.5"
    ::= { ieee1588BaseEnumClockClass 117 }

ieee1588BaseEnumCcAltPtpProfile118 OBJECT-IDENTITY
    STATUS       current
    DESCRIPTION
        "ClockClass 118: For use by alternate PTP Profiles"
    REFERENCE    "IEEE 1588-2019: clause 7.6.2.5"
    ::= { ieee1588BaseEnumClockClass 118 }

ieee1588BaseEnumCcAltPtpProfile119 OBJECT-IDENTITY
    STATUS       current
    DESCRIPTION
        "ClockClass 119: For use by alternate PTP Profiles"
    REFERENCE    "IEEE 1588-2019: clause 7.6.2.5"
    ::= { ieee1588BaseEnumClockClass 119 }

ieee1588BaseEnumCcAltPtpProfile120 OBJECT-IDENTITY
    STATUS       current
    DESCRIPTION
        "ClockClass 120: For use by alternate PTP Profiles"
    REFERENCE    "IEEE 1588-2019: clause 7.6.2.5"
    ::= { ieee1588BaseEnumClockClass 120 }

ieee1588BaseEnumCcAltPtpProfile121 OBJECT-IDENTITY
    STATUS       current
    DESCRIPTION
        "ClockClass 121: For use by alternate PTP Profiles"
    REFERENCE    "IEEE 1588-2019: clause 7.6.2.5"
    ::= { ieee1588BaseEnumClockClass 121 }

ieee1588BaseEnumCcAltPtpProfile122 OBJECT-IDENTITY
    STATUS       current
    DESCRIPTION
        "ClockClass 122: For use by alternate PTP Profiles"
    REFERENCE    "IEEE 1588-2019: clause 7.6.2.5"
    ::= { ieee1588BaseEnumClockClass 122 }

ieee1588BaseEnumCcAltPtpProfile133 OBJECT-IDENTITY
    STATUS       current
    DESCRIPTION
        "ClockClass 133: For use by alternate PTP Profiles"
    REFERENCE    "IEEE 1588-2019: clause 7.6.2.5"
    ::= { ieee1588BaseEnumClockClass 133 }

ieee1588BaseEnumCcAltPtpProfile134 OBJECT-IDENTITY
    STATUS       current
    DESCRIPTION
        "ClockClass 134: For use by alternate PTP Profiles"
    REFERENCE    "IEEE 1588-2019: clause 7.6.2.5"
    ::= { ieee1588BaseEnumClockClass 134 }

ieee1588BaseEnumCcAltPtpProfile135 OBJECT-IDENTITY
    STATUS       current
    DESCRIPTION
        "ClockClass 135: For use by alternate PTP Profiles"
    REFERENCE    "IEEE 1588-2019: clause 7.6.2.5"
    ::= { ieee1588BaseEnumClockClass 135 }

ieee1588BaseEnumCcAltPtpProfile136 OBJECT-IDENTITY
    STATUS       current
    DESCRIPTION
        "ClockClass 136: For use by alternate PTP Profiles"
    REFERENCE    "IEEE 1588-2019: clause 7.6.2.5"
    ::= { ieee1588BaseEnumClockClass 136 }

ieee1588BaseEnumCcAltPtpProfile137 OBJECT-IDENTITY
    STATUS       current
    DESCRIPTION
        "ClockClass 137: For use by alternate PTP Profiles"
    REFERENCE    "IEEE 1588-2019: clause 7.6.2.5"
    ::= { ieee1588BaseEnumClockClass 137 }

ieee1588BaseEnumCcAltPtpProfile138 OBJECT-IDENTITY
    STATUS       current
    DESCRIPTION
        "ClockClass 138: For use by alternate PTP Profiles"
    REFERENCE    "IEEE 1588-2019: clause 7.6.2.5"
    ::= { ieee1588BaseEnumClockClass 138 }

ieee1588BaseEnumCcAltPtpProfile139 OBJECT-IDENTITY
    STATUS       current
    DESCRIPTION
        "ClockClass 139: For use by alternate PTP Profiles"
    REFERENCE    "IEEE 1588-2019: clause 7.6.2.5"
    ::= { ieee1588BaseEnumClockClass 139 }

ieee1588BaseEnumCcAltPtpProfile140 OBJECT-IDENTITY
    STATUS       current
    DESCRIPTION
        "ClockClass 140: For use by alternate PTP Profiles"
    REFERENCE    "IEEE 1588-2019: clause 7.6.2.5"
    ::= { ieee1588BaseEnumClockClass 140 }

ieee1588BaseEnumCcAltPtpProfile141 OBJECT-IDENTITY
    STATUS       current
    DESCRIPTION
        "ClockClass 141: For use by alternate PTP Profiles"
    REFERENCE    "IEEE 1588-2019: clause 7.6.2.5"
    ::= { ieee1588BaseEnumClockClass 141 }

ieee1588BaseEnumCcAltPtpProfile142 OBJECT-IDENTITY
    STATUS       current
    DESCRIPTION
        "ClockClass 142: For use by alternate PTP Profiles"
    REFERENCE    "IEEE 1588-2019: clause 7.6.2.5"
    ::= { ieee1588BaseEnumClockClass 142 }

ieee1588BaseEnumCcAltPtpProfile143 OBJECT-IDENTITY
    STATUS       current
    DESCRIPTION
        "ClockClass 143: For use by alternate PTP Profiles"
    REFERENCE    "IEEE 1588-2019: clause 7.6.2.5"
    ::= { ieee1588BaseEnumClockClass 143 }

ieee1588BaseEnumCcAltPtpProfile144 OBJECT-IDENTITY
    STATUS       current
    DESCRIPTION
        "ClockClass 144: For use by alternate PTP Profiles"
    REFERENCE    "IEEE 1588-2019: clause 7.6.2.5"
    ::= { ieee1588BaseEnumClockClass 144 }

ieee1588BaseEnumCcAltPtpProfile145 OBJECT-IDENTITY
    STATUS       current
    DESCRIPTION
        "ClockClass 145: For use by alternate PTP Profiles"
    REFERENCE    "IEEE 1588-2019: clause 7.6.2.5"
    ::= { ieee1588BaseEnumClockClass 145 }

ieee1588BaseEnumCcAltPtpProfile146 OBJECT-IDENTITY
    STATUS       current
    DESCRIPTION
        "ClockClass 146: For use by alternate PTP Profiles"
    REFERENCE    "IEEE 1588-2019: clause 7.6.2.5"
    ::= { ieee1588BaseEnumClockClass 146 }

ieee1588BaseEnumCcAltPtpProfile147 OBJECT-IDENTITY
    STATUS       current
    DESCRIPTION
        "ClockClass 147: For use by alternate PTP Profiles"
    REFERENCE    "IEEE 1588-2019: clause 7.6.2.5"
    ::= { ieee1588BaseEnumClockClass 147 }

ieee1588BaseEnumCcAltPtpProfile148 OBJECT-IDENTITY
    STATUS       current
    DESCRIPTION
        "ClockClass 148: For use by alternate PTP Profiles"
    REFERENCE    "IEEE 1588-2019: clause 7.6.2.5"
    ::= { ieee1588BaseEnumClockClass 148 }

ieee1588BaseEnumCcAltPtpProfile149 OBJECT-IDENTITY
    STATUS       current
    DESCRIPTION
        "ClockClass 149: For use by alternate PTP Profiles"
    REFERENCE    "IEEE 1588-2019: clause 7.6.2.5"
    ::= { ieee1588BaseEnumClockClass 149 }

ieee1588BaseEnumCcAltPtpProfile150 OBJECT-IDENTITY
    STATUS       current
    DESCRIPTION
        "ClockClass 150: For use by alternate PTP Profiles"
    REFERENCE    "IEEE 1588-2019: clause 7.6.2.5"
    ::= { ieee1588BaseEnumClockClass 150 }

ieee1588BaseEnumCcAltPtpProfile151 OBJECT-IDENTITY
    STATUS       current
    DESCRIPTION
        "ClockClass 151: For use by alternate PTP Profiles"
    REFERENCE    "IEEE 1588-2019: clause 7.6.2.5"
    ::= { ieee1588BaseEnumClockClass 151 }

ieee1588BaseEnumCcAltPtpProfile152 OBJECT-IDENTITY
    STATUS       current
    DESCRIPTION
        "ClockClass 152: For use by alternate PTP Profiles"
    REFERENCE    "IEEE 1588-2019: clause 7.6.2.5"
    ::= { ieee1588BaseEnumClockClass 152 }

ieee1588BaseEnumCcAltPtpProfile153 OBJECT-IDENTITY
    STATUS       current
    DESCRIPTION
        "ClockClass 153: For use by alternate PTP Profiles"
    REFERENCE    "IEEE 1588-2019: clause 7.6.2.5"
    ::= { ieee1588BaseEnumClockClass 153 }

ieee1588BaseEnumCcAltPtpProfile154 OBJECT-IDENTITY
    STATUS       current
    DESCRIPTION
        "ClockClass 154: For use by alternate PTP Profiles"
    REFERENCE    "IEEE 1588-2019: clause 7.6.2.5"
    ::= { ieee1588BaseEnumClockClass 154 }

ieee1588BaseEnumCcAltPtpProfile155 OBJECT-IDENTITY
    STATUS       current
    DESCRIPTION
        "ClockClass 155: For use by alternate PTP Profiles"
    REFERENCE    "IEEE 1588-2019: clause 7.6.2.5"
    ::= { ieee1588BaseEnumClockClass 155 }

ieee1588BaseEnumCcAltPtpProfile156 OBJECT-IDENTITY
    STATUS       current
    DESCRIPTION
        "ClockClass 156: For use by alternate PTP Profiles"
    REFERENCE    "IEEE 1588-2019: clause 7.6.2.5"
    ::= { ieee1588BaseEnumClockClass 156 }

ieee1588BaseEnumCcAltPtpProfile157 OBJECT-IDENTITY
    STATUS       current
    DESCRIPTION
        "ClockClass 157: For use by alternate PTP Profiles"
    REFERENCE    "IEEE 1588-2019: clause 7.6.2.5"
    ::= { ieee1588BaseEnumClockClass 157 }

ieee1588BaseEnumCcAltPtpProfile158 OBJECT-IDENTITY
    STATUS       current
    DESCRIPTION
        "ClockClass 158: For use by alternate PTP Profiles"
    REFERENCE    "IEEE 1588-2019: clause 7.6.2.5"
    ::= { ieee1588BaseEnumClockClass 158 }

ieee1588BaseEnumCcAltPtpProfile159 OBJECT-IDENTITY
    STATUS       current
    DESCRIPTION
        "ClockClass 159: For use by alternate PTP Profiles"
    REFERENCE    "IEEE 1588-2019: clause 7.6.2.5"
    ::= { ieee1588BaseEnumClockClass 159 }

ieee1588BaseEnumCcAltPtpProfile160 OBJECT-IDENTITY
    STATUS       current
    DESCRIPTION
        "ClockClass 160: For use by alternate PTP Profiles"
    REFERENCE    "IEEE 1588-2019: clause 7.6.2.5"
    ::= { ieee1588BaseEnumClockClass 160 }

ieee1588BaseEnumCcAltPtpProfile161 OBJECT-IDENTITY
    STATUS       current
    DESCRIPTION
        "ClockClass 161: For use by alternate PTP Profiles"
    REFERENCE    "IEEE 1588-2019: clause 7.6.2.5"
    ::= { ieee1588BaseEnumClockClass 161 }

ieee1588BaseEnumCcAltPtpProfile162 OBJECT-IDENTITY
    STATUS       current
    DESCRIPTION
        "ClockClass 162: For use by alternate PTP Profiles"
    REFERENCE    "IEEE 1588-2019: clause 7.6.2.5"
    ::= { ieee1588BaseEnumClockClass 162 }

ieee1588BaseEnumCcAltPtpProfile163 OBJECT-IDENTITY
    STATUS       current
    DESCRIPTION
        "ClockClass 163: For use by alternate PTP Profiles"
    REFERENCE    "IEEE 1588-2019: clause 7.6.2.5"
    ::= { ieee1588BaseEnumClockClass 163 }

ieee1588BaseEnumCcAltPtpProfile164 OBJECT-IDENTITY
    STATUS       current
    DESCRIPTION
        "ClockClass 164: For use by alternate PTP Profiles"
    REFERENCE    "IEEE 1588-2019: clause 7.6.2.5"
    ::= { ieee1588BaseEnumClockClass 164 }

ieee1588BaseEnumCcAltPtpProfile165 OBJECT-IDENTITY
    STATUS       current
    DESCRIPTION
        "ClockClass 165: For use by alternate PTP Profiles"
    REFERENCE    "IEEE 1588-2019: clause 7.6.2.5"
    ::= { ieee1588BaseEnumClockClass 165 }

ieee1588BaseEnumCcAltPtpProfile166 OBJECT-IDENTITY
    STATUS       current
    DESCRIPTION
        "ClockClass 166: For use by alternate PTP Profiles"
    REFERENCE    "IEEE 1588-2019: clause 7.6.2.5"
    ::= { ieee1588BaseEnumClockClass 166 }

ieee1588BaseEnumCcAltPtpProfile167 OBJECT-IDENTITY
    STATUS       current
    DESCRIPTION
        "ClockClass 167: For use by alternate PTP Profiles"
    REFERENCE    "IEEE 1588-2019: clause 7.6.2.5"
    ::= { ieee1588BaseEnumClockClass 167 }

ieee1588BaseEnumCcAltPtpProfile168 OBJECT-IDENTITY
    STATUS       current
    DESCRIPTION
        "ClockClass 168: For use by alternate PTP Profiles"
    REFERENCE    "IEEE 1588-2019: clause 7.6.2.5"
    ::= { ieee1588BaseEnumClockClass 168 }

ieee1588BaseEnumCcAltPtpProfile169 OBJECT-IDENTITY
    STATUS       current
    DESCRIPTION
        "ClockClass 169: For use by alternate PTP Profiles"
    REFERENCE    "IEEE 1588-2019: clause 7.6.2.5"
    ::= { ieee1588BaseEnumClockClass 169 }

ieee1588BaseEnumCcAltPtpProfile170 OBJECT-IDENTITY
    STATUS       current
    DESCRIPTION
        "ClockClass 170: For use by alternate PTP Profiles"
    REFERENCE    "IEEE 1588-2019: clause 7.6.2.5"
    ::= { ieee1588BaseEnumClockClass 170 }

ieee1588BaseEnumCcPrimaryHoldoverDegradationB OBJECT-IDENTITY
    STATUS       current
    DESCRIPTION
        "ClockClass 187: Degradation alternative B for a PTP Instance of
        clockClass 7 that is not within holdover specification or that
        is based on the specifications of the Holdover."
    REFERENCE    "IEEE 1588-2019: clause 7.6.2.5"
    ::= { ieee1588BaseEnumClockClass 187 }

ieee1588BaseEnumCcApplicationSpecficHoldoverDegradationB OBJECT-IDENTITY
    STATUS       current
    DESCRIPTION
        "ClockClass 193: Degradation alternative B for a PTP Instance of
        clockClass 14 that is not within holdover specification or that
        is based on the specifications of the Holdover."
    REFERENCE    "IEEE 1588-2019: clause 7.6.2.5"
    ::= { ieee1588BaseEnumClockClass 193 }

ieee1588BaseEnumCcAltPtpProfile216 OBJECT-IDENTITY
    STATUS       current
    DESCRIPTION
        "ClockClass 216: For use by alternate PTP Profiles"
    REFERENCE    "IEEE 1588-2019: clause 7.6.2.5"
    ::= { ieee1588BaseEnumClockClass 216 }

ieee1588BaseEnumCcAltPtpProfile217 OBJECT-IDENTITY
    STATUS       current
    DESCRIPTION
        "ClockClass 217: For use by alternate PTP Profiles"
    REFERENCE    "IEEE 1588-2019: clause 7.6.2.5"
    ::= { ieee1588BaseEnumClockClass 217 }

ieee1588BaseEnumCcAltPtpProfile218 OBJECT-IDENTITY
    STATUS       current
    DESCRIPTION
        "ClockClass 218: For use by alternate PTP Profiles"
    REFERENCE    "IEEE 1588-2019: clause 7.6.2.5"
    ::= { ieee1588BaseEnumClockClass 218 }

ieee1588BaseEnumCcAltPtpProfile219 OBJECT-IDENTITY
    STATUS       current
    DESCRIPTION
        "ClockClass 219: For use by alternate PTP Profiles"
    REFERENCE    "IEEE 1588-2019: clause 7.6.2.5"
    ::= { ieee1588BaseEnumClockClass 219 }

ieee1588BaseEnumCcAltPtpProfile220 OBJECT-IDENTITY
    STATUS       current
    DESCRIPTION
        "ClockClass 220: For use by alternate PTP Profiles"
    REFERENCE    "IEEE 1588-2019: clause 7.6.2.5"
    ::= { ieee1588BaseEnumClockClass 220 }

ieee1588BaseEnumCcAltPtpProfile221 OBJECT-IDENTITY
    STATUS       current
    DESCRIPTION
        "ClockClass 221: For use by alternate PTP Profiles"
    REFERENCE    "IEEE 1588-2019: clause 7.6.2.5"
    ::= { ieee1588BaseEnumClockClass 221 }

ieee1588BaseEnumCcAltPtpProfile222 OBJECT-IDENTITY
    STATUS       current
    DESCRIPTION
        "ClockClass 222: For use by alternate PTP Profiles"
    REFERENCE    "IEEE 1588-2019: clause 7.6.2.5"
    ::= { ieee1588BaseEnumClockClass 222 }

ieee1588BaseEnumCcAltPtpProfile223 OBJECT-IDENTITY
    STATUS       current
    DESCRIPTION
        "ClockClass 223: For use by alternate PTP Profiles"
    REFERENCE    "IEEE 1588-2019: clause 7.6.2.5"
    ::= { ieee1588BaseEnumClockClass 223 }

ieee1588BaseEnumCcAltPtpProfile224 OBJECT-IDENTITY
    STATUS       current
    DESCRIPTION
        "ClockClass 224: For use by alternate PTP Profiles"
    REFERENCE    "IEEE 1588-2019: clause 7.6.2.5"
    ::= { ieee1588BaseEnumClockClass 224 }

ieee1588BaseEnumCcAltPtpProfile225 OBJECT-IDENTITY
    STATUS       current
    DESCRIPTION
        "ClockClass 225: For use by alternate PTP Profiles"
    REFERENCE    "IEEE 1588-2019: clause 7.6.2.5"
    ::= { ieee1588BaseEnumClockClass 225 }

ieee1588BaseEnumCcAltPtpProfile226 OBJECT-IDENTITY
    STATUS       current
    DESCRIPTION
        "ClockClass 226: For use by alternate PTP Profiles"
    REFERENCE    "IEEE 1588-2019: clause 7.6.2.5"
    ::= { ieee1588BaseEnumClockClass 226 }

ieee1588BaseEnumCcAltPtpProfile227 OBJECT-IDENTITY
    STATUS       current
    DESCRIPTION
        "ClockClass 227: For use by alternate PTP Profiles"
    REFERENCE    "IEEE 1588-2019: clause 7.6.2.5"
    ::= { ieee1588BaseEnumClockClass 227 }

ieee1588BaseEnumCcAltPtpProfile228 OBJECT-IDENTITY
    STATUS       current
    DESCRIPTION
        "ClockClass 228: For use by alternate PTP Profiles"
    REFERENCE    "IEEE 1588-2019: clause 7.6.2.5"
    ::= { ieee1588BaseEnumClockClass 228 }

ieee1588BaseEnumCcAltPtpProfile229 OBJECT-IDENTITY
    STATUS       current
    DESCRIPTION
        "ClockClass 229: For use by alternate PTP Profiles"
    REFERENCE    "IEEE 1588-2019: clause 7.6.2.5"
    ::= { ieee1588BaseEnumClockClass 229 }

ieee1588BaseEnumCcAltPtpProfile230 OBJECT-IDENTITY
    STATUS       current
    DESCRIPTION
        "ClockClass 230: For use by alternate PTP Profiles"
    REFERENCE    "IEEE 1588-2019: clause 7.6.2.5"
    ::= { ieee1588BaseEnumClockClass 230 }

ieee1588BaseEnumCcAltPtpProfile231 OBJECT-IDENTITY
    STATUS       current
    DESCRIPTION
        "ClockClass 231: For use by alternate PTP Profiles"
    REFERENCE    "IEEE 1588-2019: clause 7.6.2.5"
    ::= { ieee1588BaseEnumClockClass 231 }

ieee1588BaseEnumCcAltPtpProfile232 OBJECT-IDENTITY
    STATUS       current
    DESCRIPTION
        "ClockClass 232: For use by alternate PTP Profiles"
    REFERENCE    "IEEE 1588-2019: clause 7.6.2.5"
    ::= { ieee1588BaseEnumClockClass 232 }

ieee1588BaseEnumCcDefault OBJECT-IDENTITY
    STATUS       current
    DESCRIPTION
        "ClockClass 248: Default Clock Class, none of the other
        clockClass definitions apply."
    REFERENCE    "IEEE 1588-2019: clause 7.6.2.5"
    ::= { ieee1588BaseEnumClockClass 248 }

ieee1588BaseEnumCcSlaveOnlyClock OBJECT-IDENTITY
    STATUS       current
    DESCRIPTION
        "ClockClass 255: Clock Class is set to slave-only PTP Instance."
    REFERENCE    "IEEE 1588-2019: clause 7.6.2.5"
    ::= { ieee1588BaseEnumClockClass 255 }

-- Enumeration for the path delay measuring mechanisms.
ieee1588BaseEnumDelayMechanism
                            OBJECT IDENTIFIER ::= { ieee1588BaseEnum 3 }

ieee1588BaseEnumDmE2e OBJECT-IDENTITY
    STATUS       current
    DESCRIPTION
        "The PTP Port is configured to use the delay request-response
        mechanism."
    REFERENCE    "IEEE 1588-2019: clause 8.2.15.4.4"
    ::= { ieee1588BaseEnumDelayMechanism 1 }

ieee1588BaseEnumDmP2p OBJECT-IDENTITY
    STATUS       current
    DESCRIPTION
        "The PTP Port is configured to use the peer-to-peer delay
        mechanism."
    REFERENCE    "IEEE 1588-2019: clause 8.2.15.4.4"
    ::= { ieee1588BaseEnumDelayMechanism 2 }

ieee1588BaseEnumDmCommonP2p OBJECT-IDENTITY
    STATUS       current
    DESCRIPTION
        "The PTP Port is configured to use the Common Mean Link Delay
        Service option."
    REFERENCE    "IEEE 1588-2019: clause 8.2.15.4.4"
    ::= { ieee1588BaseEnumDelayMechanism 3 }

ieee1588BaseEnumDmSpecial OBJECT-IDENTITY
    STATUS       current
    DESCRIPTION
        "The PTP Port is a Special Port that does not use either delay
        mechanism."
    REFERENCE    "IEEE 1588-2019: clause 8.2.15.4.4"
    ::= { ieee1588BaseEnumDelayMechanism 4 }

ieee1588BaseEnumDmNoMechanism OBJECT-IDENTITY
    STATUS       current
    DESCRIPTION
        "The PTP Port does not implement the delay mechanism. This value
        shall not be used except when the applicable PTP Profile
        specifies either:
        1) that the PTP Instance only supports frequency transfer
        (syntonization) and that neither path delay mechanism is to be
        used or
        2) that the PTP Instance participates in time transfer, but the
        system accuracy requirements are such that, for a segment of the
        system path, Delays can be neglected allowing PTP Instances in
        that portion of the PTP Network to use the disabled value."
    REFERENCE    "IEEE 1588-2019: clause 8.2.15.4.4"
    ::= { ieee1588BaseEnumDelayMechanism 254 }

-- Enumeration of a type of PTP Instance. Values not defined in this
-- group are reserved.
ieee1588BaseEnumInstanceType
                            OBJECT IDENTIFIER ::= { ieee1588BaseEnum 4 }

ieee1588BaseEnumItOrdinaryClock OBJECT-IDENTITY
    STATUS       current
    DESCRIPTION
        "The PTP Instance is configured as Ordinary Clock (OC)"
    REFERENCE    "IEEE 1588-2019: clause 8.2.1.5.5"
    ::= { ieee1588BaseEnumInstanceType 0 }

ieee1588BaseEnumItBoundaryClock OBJECT-IDENTITY
    STATUS       current
    DESCRIPTION
        "The PTP Instance is configured as Boundary Clock (BC)"
    REFERENCE    "IEEE 1588-2019: clause 8.2.1.5.5"
    ::= { ieee1588BaseEnumInstanceType 1 }

ieee1588BaseEnumItPeerToPeerTransparentClock OBJECT-IDENTITY
    STATUS       current
    DESCRIPTION
        "The PTP Instance is configured as peer-to-peer Transparent
        Clock (TC)"
    REFERENCE    "IEEE 1588-2019: clause 8.2.1.5.5"
    ::= { ieee1588BaseEnumInstanceType 2 }

ieee1588BaseEnumItEndToEndTransparentClock OBJECT-IDENTITY
    STATUS       current
    DESCRIPTION
        "The PTP Instance is configured as end-to-end Transparent Clock
        (TC)"
    REFERENCE    "IEEE 1588-2019: clause 8.2.1.5.5"
    ::= { ieee1588BaseEnumInstanceType 3 }

-- Enumeration of states of an L1Sync port.
ieee1588BaseEnumL1SyncState OBJECT IDENTIFIER ::= { ieee1588BaseEnum 5 }

ieee1588BaseEnumL1SsDisabled OBJECT-IDENTITY
    STATUS       current
    DESCRIPTION
        "L1Sync is not enabled on this PTP Port, or the event
        L1SYNC_RESET has occurred."
    REFERENCE    "IEEE 1588-2019: clause L.5.3.5"
    ::= { ieee1588BaseEnumL1SyncState 1 }

ieee1588BaseEnumL1SsIdle OBJECT-IDENTITY
    STATUS       current
    DESCRIPTION
        "L1Sync is enabled on this PTP Port. The PTP Port sends messages
        with the L1_SYNC TLV. Initialization occurs in this state."
    REFERENCE    "IEEE 1588-2019: clause L.5.3.5"
    ::= { ieee1588BaseEnumL1SyncState 2 }

ieee1588BaseEnumL1SsLinkAlive OBJECT-IDENTITY
    STATUS       current
    DESCRIPTION
        "The PTP Port sends messages with the L1_SYNC TLV. The PTP Port
        is receiving valid L1_SYNC TLV from a peer PTP Port."
    REFERENCE    "IEEE 1588-2019: clause L.5.3.5"
    ::= { ieee1588BaseEnumL1SyncState 3 }

ieee1588BaseEnumL1SsConfigMatch OBJECT-IDENTITY
    STATUS       current
    DESCRIPTION
        "The PTP Port sends messages with the L1_SYNC TLV. The PTP Port
        has a compatible configuration profile when compared with its
        peer PTP Port configuration profile received in the L1_SYNC
        TLV."
    REFERENCE    "IEEE 1588-2019: clause L.5.3.5"
    ::= { ieee1588BaseEnumL1SyncState 4 }

ieee1588BaseEnumL1SsL1SyncUp OBJECT-IDENTITY
    STATUS       current
    DESCRIPTION
        "The PTP Port sends messages with the L1_SYNC TLV. The
        relationship required by configuration is currently in place.
        Synchronization enhancements are performed."
    REFERENCE    "IEEE 1588-2019: clause L.5.3.5"
    ::= { ieee1588BaseEnumL1SyncState 5 }

-- Enumeration of type of the PTP messages.
ieee1588BaseEnumMessageType OBJECT IDENTIFIER ::= { ieee1588BaseEnum 6 }

ieee1588BaseEnumMtSync OBJECT-IDENTITY
    STATUS       current
    DESCRIPTION
        "Sync message"
    REFERENCE    "IEEE 1588-2019: clause 13.3.2.3"
    ::= { ieee1588BaseEnumMessageType 0 }

ieee1588BaseEnumMtDelayReq OBJECT-IDENTITY
    STATUS       current
    DESCRIPTION
        "Delay_Req message"
    REFERENCE    "IEEE 1588-2019: clause 13.3.2.3"
    ::= { ieee1588BaseEnumMessageType 1 }

ieee1588BaseEnumMtPdelayReq OBJECT-IDENTITY
    STATUS       current
    DESCRIPTION
        "Pdelay_Req message"
    REFERENCE    "IEEE 1588-2019: clause 13.3.2.3"
    ::= { ieee1588BaseEnumMessageType 2 }

ieee1588BaseEnumMtPdelayResp OBJECT-IDENTITY
    STATUS       current
    DESCRIPTION
        "Pdelay_Resp message"
    REFERENCE    "IEEE 1588-2019: clause 13.3.2.3"
    ::= { ieee1588BaseEnumMessageType 3 }

ieee1588BaseEnumMtFollowUp OBJECT-IDENTITY
    STATUS       current
    DESCRIPTION
        "Follow_Up message"
    REFERENCE    "IEEE 1588-2019: clause 13.3.2.3"
    ::= { ieee1588BaseEnumMessageType 8 }

ieee1588BaseEnumMtDelayResp OBJECT-IDENTITY
    STATUS       current
    DESCRIPTION
        "Delay_Resp message"
    REFERENCE    "IEEE 1588-2019: clause 13.3.2.3"
    ::= { ieee1588BaseEnumMessageType 9 }

ieee1588BaseEnumMtPdelayRespFollowUp OBJECT-IDENTITY
    STATUS       current
    DESCRIPTION
        "Pdelay_Resp_Follow_Up message"
    REFERENCE    "IEEE 1588-2019: clause 13.3.2.3"
    ::= { ieee1588BaseEnumMessageType 10 }

ieee1588BaseEnumMtAnnounce OBJECT-IDENTITY
    STATUS       current
    DESCRIPTION
        "Announce message"
    REFERENCE    "IEEE 1588-2019: clause 13.3.2.3"
    ::= { ieee1588BaseEnumMessageType 11 }

ieee1588BaseEnumMtSignaling OBJECT-IDENTITY
    STATUS       current
    DESCRIPTION
        "Signaling message"
    REFERENCE    "IEEE 1588-2019: clause 13.3.2.3"
    ::= { ieee1588BaseEnumMessageType 12 }

ieee1588BaseEnumMtManagement OBJECT-IDENTITY
    STATUS       current
    DESCRIPTION
        "Management message"
    REFERENCE    "IEEE 1588-2019: clause 13.3.2.3"
    ::= { ieee1588BaseEnumMessageType 13 }

-- Group contains enumeration of the protocol used by a PTP Instance to
-- transport PTP messages. The additional values are defined:
-- 0 - Reserved
-- 0008-EFFF - Reserved
-- F000-FFFD - Designated for assignment in a PTP Profile
-- FFFF - Reserved
-- Enumeration assignments for other transport mechanisms will be
-- assigned when the appropriate mapping annex is added to IEEE Std 1588
-- standard by amendment or in a future edition.
ieee1588BaseEnumNetworkProtocol
                            OBJECT IDENTIFIER ::= { ieee1588BaseEnum 7 }

ieee1588BaseEnumNpUdpIpv4 OBJECT-IDENTITY
    STATUS       current
    DESCRIPTION
        "UDP on IPv4"
    REFERENCE    "IEEE 1588-2019: clause 7.4.1, Annex C"
    ::= { ieee1588BaseEnumNetworkProtocol 1 }

ieee1588BaseEnumNpUdpIPv6 OBJECT-IDENTITY
    STATUS       current
    DESCRIPTION
        "UDP on IPv6"
    REFERENCE    "IEEE 1588-2019: clause 7.4.1, Annex D"
    ::= { ieee1588BaseEnumNetworkProtocol 2 }

ieee1588BaseEnumNpIeee8023 OBJECT-IDENTITY
    STATUS       current
    DESCRIPTION
        "IEEE Std 802.3 (Ethernet)"
    REFERENCE    "IEEE 1588-2019: clause 7.4.1, Annex E"
    ::= { ieee1588BaseEnumNetworkProtocol 3 }

ieee1588BaseEnumNpDeviceNet OBJECT-IDENTITY
    STATUS       current
    DESCRIPTION
        "DeviceNet"
    REFERENCE    "IEEE 1588-2019: clause 7.4.1, Annex F"
    ::= { ieee1588BaseEnumNetworkProtocol 4 }

ieee1588BaseEnumNpControlNet OBJECT-IDENTITY
    STATUS       current
    DESCRIPTION
        "ControlNet"
    REFERENCE    "IEEE 1588-2019: clause 7.4.1, Annex G"
    ::= { ieee1588BaseEnumNetworkProtocol 5 }

ieee1588BaseEnumNpProfinet OBJECT-IDENTITY
    STATUS       current
    DESCRIPTION
        "PROFINET"
    REFERENCE    "IEEE 1588-2019: clause 7.4.1, Annex H"
    ::= { ieee1588BaseEnumNetworkProtocol 6 }

ieee1588BaseEnumNpOtn OBJECT-IDENTITY
    STATUS       current
    DESCRIPTION
        "Optical Transport Network (OTN)"
    REFERENCE    "IEEE 1588b-2022: clause 7.4.1, Annex H1"
    ::= { ieee1588BaseEnumNetworkProtocol 7 }

ieee1588BaseEnumNpUnknown OBJECT-IDENTITY
    STATUS       current
    DESCRIPTION
        "Unknown Protocol"
    REFERENCE    "IEEE 1588-2019: clause 7.4.1"
    ::= { ieee1588BaseEnumNetworkProtocol 65534 }

-- Enumeration of the possible values for the state of the protocol
-- engine associated with the PTP Port.
ieee1588BaseEnumPortState OBJECT IDENTIFIER ::= { ieee1588BaseEnum 8 }

ieee1588BaseEnumPsInitializing OBJECT-IDENTITY
    STATUS       current
    DESCRIPTION
        "The PTP Port is initializing its data sets, hardware, and
        communication facilities. The PTP Port shall not place any PTP
        messages on its communication path."
    REFERENCE    "IEEE 1588-2019: clause 8.2.15.3.1, 9.2.5"
    ::= { ieee1588BaseEnumPortState 1 }

ieee1588BaseEnumPsFaulty OBJECT-IDENTITY
    STATUS       current
    DESCRIPTION
        "The fault state of the protocol. Except for PTP management
        messages that are a required response to a PTP message received
        from the applicable management mechanism, a PTP Port in this
        state shall not transmit any PTP related messages. In a Boundary
        Clock, no activity on a faulty PTP Port shall affect the other
        PTP Ports of the PTP Instance. If fault activity on a PTP Port
        in this state cannot be confined to the faulty PTP Port, then
        all PTP Ports shall be in the faulty state."
    REFERENCE    "IEEE 1588-2019: clause 8.2.15.3.1, 9.2.5"
    ::= { ieee1588BaseEnumPortState 2 }

ieee1588BaseEnumPsDisabled OBJECT-IDENTITY
    STATUS       current
    DESCRIPTION
        "The PTP Port is disabled. Except for PTP management messages
        that are a required response to a PTP message received from the
        applicable management mechanism, a PTP Port in this state shall
        not transmit any PTP related messages. In a Boundary Clock, no
        activity at the PTP Port shall be allowed to affect the activity
        at any other PTP Port of the Boundary Clock. A PTP Port in this
        state shall discard all received PTP messages except for PTP
        management messages."
    REFERENCE    "IEEE 1588-2019: clause 8.2.15.3.1, 9.2.5"
    ::= { ieee1588BaseEnumPortState 3 }

ieee1588BaseEnumPsListening OBJECT-IDENTITY
    STATUS       current
    DESCRIPTION
        "The PTP Port is waiting for the announce-receipt-timeout to
        expire or to receive an Announce message from a Master PTP
        Instance. The purpose of this state is to allow orderly addition
        of PTP Instances to a domain (i.e. to know if this PTP Port is
        truly a port of a Grandmaster PTP Instance prior to taking that
        role)."
    REFERENCE    "IEEE 1588-2019: clause 8.2.15.3.1, 9.2.5"
    ::= { ieee1588BaseEnumPortState 4 }

ieee1588BaseEnumPsPreMaster OBJECT-IDENTITY
    STATUS       current
    DESCRIPTION
        "The PTP Port state provides an additional mechanism to support
        more orderly reconfiguration of PTP Networks when PTP Instances
        are added or deleted, PTP Instance characteristics change, or
        connection topology changes. In this state, a PTP Port behaves
        as it would if it were in the master state except that it does
        not place certain classes of PTP messages on the PTP
        Communication Path associated with the PTP Port."
    REFERENCE    "IEEE 1588-2019: clause 8.2.15.3.1, 9.2.5"
    ::= { ieee1588BaseEnumPortState 5 }

ieee1588BaseEnumPsMaster OBJECT-IDENTITY
    STATUS       current
    DESCRIPTION
        "The PTP Port is the source of time on the PTP Communication
        Path."
    REFERENCE    "IEEE 1588-2019: clause 8.2.15.3.1, 9.2.5"
    ::= { ieee1588BaseEnumPortState 6 }

ieee1588BaseEnumPsPassive OBJECT-IDENTITY
    STATUS       current
    DESCRIPTION
        "The PTP Port is not the source of time on the PTP Communication
        Path nor does it synchronize to a Master Clock (receive time).
        The PTP Port can potentially change to slave when PTP Instances
        are added or deleted, PTP Instance characteristics change, or
        connection topology changes."
    REFERENCE    "IEEE 1588-2019: clause 8.2.15.3.1, 9.2.5"
    ::= { ieee1588BaseEnumPortState 7 }

ieee1588BaseEnumPsUncalibrated OBJECT-IDENTITY
    STATUS       current
    DESCRIPTION
        "The PTP Port is anticipating a change to the slave state, but
        it has not yet satisfied all requirements (implementation or PTP
        Profile) necessary to ensure complete synchronization. For
        example, an implementation might require a minimum number of PTP
        Sync messages in order to completely synchronize its servo
        algorithm."
    REFERENCE    "IEEE 1588-2019: clause 8.2.15.3.1, 9.2.5"
    ::= { ieee1588BaseEnumPortState 8 }

ieee1588BaseEnumPsSlave OBJECT-IDENTITY
    STATUS       current
    DESCRIPTION
        "The PTP Port synchronizes to the PTP Port on the PTP
        Communication Path that is in the master state (i.e. receives
        time)."
    REFERENCE    "IEEE 1588-2019: clause 8.2.15.3.1, 9.2.5"
    ::= { ieee1588BaseEnumPortState 9 }

-- Enumeration of the severity of a fault record.
ieee1588BaseEnumSeverityCode
                            OBJECT IDENTIFIER ::= { ieee1588BaseEnum 9 }

ieee1588BaseEnumScEmergency OBJECT-IDENTITY
    STATUS       current
    DESCRIPTION
        "System is unusable"
    REFERENCE    "IEEE 1588-2019: clause 8.2.6.3"
    ::= { ieee1588BaseEnumSeverityCode 0 }

ieee1588BaseEnumScAlert OBJECT-IDENTITY
    STATUS       current
    DESCRIPTION
        "Immediate action needed"
    REFERENCE    "IEEE 1588-2019: clause 8.2.6.3"
    ::= { ieee1588BaseEnumSeverityCode 1 }

ieee1588BaseEnumScCritical OBJECT-IDENTITY
    STATUS       current
    DESCRIPTION
        "Critical conditions"
    REFERENCE    "IEEE 1588-2019: clause 8.2.6.3"
    ::= { ieee1588BaseEnumSeverityCode 2 }

ieee1588BaseEnumScError OBJECT-IDENTITY
    STATUS       current
    DESCRIPTION
        "Error conditions"
    REFERENCE    "IEEE 1588-2019: clause 8.2.6.3"
    ::= { ieee1588BaseEnumSeverityCode 3 }

ieee1588BaseEnumScWarning OBJECT-IDENTITY
    STATUS       current
    DESCRIPTION
        "Warning conditions"
    REFERENCE    "IEEE 1588-2019: clause 8.2.6.3"
    ::= { ieee1588BaseEnumSeverityCode 4 }

ieee1588BaseEnumScNotice OBJECT-IDENTITY
    STATUS       current
    DESCRIPTION
        "Normal but significant condition"
    REFERENCE    "IEEE 1588-2019: clause 8.2.6.3"
    ::= { ieee1588BaseEnumSeverityCode 5 }

ieee1588BaseEnumScInformational OBJECT-IDENTITY
    STATUS       current
    DESCRIPTION
        "Informational messages"
    REFERENCE    "IEEE 1588-2019: clause 8.2.6.3"
    ::= { ieee1588BaseEnumSeverityCode 6 }

ieee1588BaseEnumScDebug OBJECT-IDENTITY
    STATUS       current
    DESCRIPTION
        "Debug-level messages"
    REFERENCE    "IEEE 1588-2019: clause 8.2.6.3"
    ::= { ieee1588BaseEnumSeverityCode 7 }

-- Enumeration of attribute indicating the type of source of time used
-- by a grandmaster clock.
ieee1588BaseEnumTimeSource OBJECT IDENTIFIER ::= { ieee1588BaseEnum 10 }

ieee1588BaseEnumTsAtomicClock OBJECT-IDENTITY
    STATUS       current
    DESCRIPTION
        "Any PTP Instance that is based on an atomic resonance for
        frequency, or a PTP Instance directly connected to a device that
        is based on an atomic resonance for frequency."
    REFERENCE    "IEEE 1588-2019: clause 7.6.2.8"
    ::= { ieee1588BaseEnumTimeSource 16 }

ieee1588BaseEnumTsGnss OBJECT-IDENTITY
    STATUS       current
    DESCRIPTION
        "Any PTP Instance synchronized to a satellite system that
        distributes time and frequency."
    REFERENCE    "IEEE 1588-2019: clause 7.6.2.8"
    ::= { ieee1588BaseEnumTimeSource 32 }

ieee1588BaseEnumTsTerrestrialRadio OBJECT-IDENTITY
    STATUS       current
    DESCRIPTION
        "Any PTP Instance synchronized via any of the radio distribution
        systems that distribute time and frequency."
    REFERENCE    "IEEE 1588-2019: clause 7.6.2.8"
    ::= { ieee1588BaseEnumTimeSource 48 }

ieee1588BaseEnumTsSerialTimeCode OBJECT-IDENTITY
    STATUS       current
    DESCRIPTION
        "Any PTP Instance synchronized via any of the serial time code
        distribution systems that distribute time and frequency, for
        example, IRIG-B."
    REFERENCE    "IEEE 1588-2019: clause 7.6.2.8"
    ::= { ieee1588BaseEnumTimeSource 57 }

ieee1588BaseEnumTsPtp OBJECT-IDENTITY
    STATUS       current
    DESCRIPTION
        "Any PTP Instance synchronized to a PTP-based source of time
        external to the domain."
    REFERENCE    "IEEE 1588-2019: clause 7.6.2.8"
    ::= { ieee1588BaseEnumTimeSource 64 }

ieee1588BaseEnumTsNtp OBJECT-IDENTITY
    STATUS       current
    DESCRIPTION
        "Any PTP Instance synchronized via NTP or Simple Network Time
        Protocol (SNTP) servers that distribute time and frequency."
    REFERENCE    "IEEE 1588-2019: clause 7.6.2.8"
    ::= { ieee1588BaseEnumTimeSource 80 }

ieee1588BaseEnumTsHandSet OBJECT-IDENTITY
    STATUS       current
    DESCRIPTION
        "Used for any PTP Instance whose time has been set by means of a
        human interface based on observation of a source of time to
        within the claimed clock accuracy."
    REFERENCE    "IEEE 1588-2019: clause 7.6.2.8"
    ::= { ieee1588BaseEnumTimeSource 96 }

ieee1588BaseEnumTsOther OBJECT-IDENTITY
    STATUS       current
    DESCRIPTION
        "Other source of time and/or frequency not covered by other
        values."
    REFERENCE    "IEEE 1588-2019: clause 7.6.2.8"
    ::= { ieee1588BaseEnumTimeSource 144 }

ieee1588BaseEnumTsInternalOscillator OBJECT-IDENTITY
    STATUS       current
    DESCRIPTION
        "Any PTP Instance whose frequency is not based on atomic
        resonance, and whose time is based on a free-running oscillator
        with epoch determined in an arbitrary or unknown manner."
    REFERENCE    "IEEE 1588-2019: clause 7.6.2.8"
    ::= { ieee1588BaseEnumTimeSource 160 }

ieee1588BaseEnumtSAltPtpProfile0xF0 OBJECT-IDENTITY
    STATUS       current
    DESCRIPTION
        "TimeSource 0xF0: Designated for assignment by alternate PTP
        Profiles"
    REFERENCE    "IEEE 1588-2019: clause 7.6.2.8"
    ::= { ieee1588BaseEnumTimeSource 240 }

ieee1588BaseEnumtSAltPtpProfile0xF1 OBJECT-IDENTITY
    STATUS       current
    DESCRIPTION
        "TimeSource 0xF1: Designated for assignment by alternate PTP
        Profiles"
    REFERENCE    "IEEE 1588-2019: clause 7.6.2.8"
    ::= { ieee1588BaseEnumTimeSource 241 }

ieee1588BaseEnumtSAltPtpProfile0xF2 OBJECT-IDENTITY
    STATUS       current
    DESCRIPTION
        "TimeSource 0xF2: Designated for assignment by alternate PTP
        Profiles"
    REFERENCE    "IEEE 1588-2019: clause 7.6.2.8"
    ::= { ieee1588BaseEnumTimeSource 242 }

ieee1588BaseEnumtSAltPtpProfile0xF3 OBJECT-IDENTITY
    STATUS       current
    DESCRIPTION
        "TimeSource 0xF3: Designated for assignment by alternate PTP
        Profiles"
    REFERENCE    "IEEE 1588-2019: clause 7.6.2.8"
    ::= { ieee1588BaseEnumTimeSource 243 }

ieee1588BaseEnumtSAltPtpProfile0xF4 OBJECT-IDENTITY
    STATUS       current
    DESCRIPTION
        "TimeSource 0xF4: Designated for assignment by alternate PTP
        Profiles"
    REFERENCE    "IEEE 1588-2019: clause 7.6.2.8"
    ::= { ieee1588BaseEnumTimeSource 244 }

ieee1588BaseEnumtSAltPtpProfile0xF5 OBJECT-IDENTITY
    STATUS       current
    DESCRIPTION
        "TimeSource 0xF5: Designated for assignment by alternate PTP
        Profiles"
    REFERENCE    "IEEE 1588-2019: clause 7.6.2.8"
    ::= { ieee1588BaseEnumTimeSource 245 }

ieee1588BaseEnumtSAltPtpProfile0xF6 OBJECT-IDENTITY
    STATUS       current
    DESCRIPTION
        "TimeSource 0xF6: Designated for assignment by alternate PTP
        Profiles"
    REFERENCE    "IEEE 1588-2019: clause 7.6.2.8"
    ::= { ieee1588BaseEnumTimeSource 246 }

ieee1588BaseEnumtSAltPtpProfile0xF7 OBJECT-IDENTITY
    STATUS       current
    DESCRIPTION
        "TimeSource 0xF7: Designated for assignment by alternate PTP
        Profiles"
    REFERENCE    "IEEE 1588-2019: clause 7.6.2.8"
    ::= { ieee1588BaseEnumTimeSource 247 }

ieee1588BaseEnumtSAltPtpProfile0xF8 OBJECT-IDENTITY
    STATUS       current
    DESCRIPTION
        "TimeSource 0xF8: Designated for assignment by alternate PTP
        Profiles"
    REFERENCE    "IEEE 1588-2019: clause 7.6.2.8"
    ::= { ieee1588BaseEnumTimeSource 248 }

ieee1588BaseEnumtSAltPtpProfile0xF9 OBJECT-IDENTITY
    STATUS       current
    DESCRIPTION
        "TimeSource 0xF9: Designated for assignment by alternate PTP
        Profiles"
    REFERENCE    "IEEE 1588-2019: clause 7.6.2.8"
    ::= { ieee1588BaseEnumTimeSource 249 }

ieee1588BaseEnumtSAltPtpProfile0xFA OBJECT-IDENTITY
    STATUS       current
    DESCRIPTION
        "TimeSource 0xFA: Designated for assignment by alternate PTP
        Profiles"
    REFERENCE    "IEEE 1588-2019: clause 7.6.2.8"
    ::= { ieee1588BaseEnumTimeSource 250 }

ieee1588BaseEnumtSAltPtpProfile0xFB OBJECT-IDENTITY
    STATUS       current
    DESCRIPTION
        "TimeSource 0xFB: Designated for assignment by alternate PTP
        Profiles"
    REFERENCE    "IEEE 1588-2019: clause 7.6.2.8"
    ::= { ieee1588BaseEnumTimeSource 251 }

ieee1588BaseEnumtSAltPtpProfile0xFC OBJECT-IDENTITY
    STATUS       current
    DESCRIPTION
        "TimeSource 0xFC: Designated for assignment by alternate PTP
        Profiles"
    REFERENCE    "IEEE 1588-2019: clause 7.6.2.8"
    ::= { ieee1588BaseEnumTimeSource 252 }

ieee1588BaseEnumtSAltPtpProfile0xFD OBJECT-IDENTITY
    STATUS       current
    DESCRIPTION
        "TimeSource 0xFD: Designated for assignment by alternate PTP
        Profiles"
    REFERENCE    "IEEE 1588-2019: clause 7.6.2.8"
    ::= { ieee1588BaseEnumTimeSource 253 }

ieee1588BaseEnumtSAltPtpProfile0xFE OBJECT-IDENTITY
    STATUS       current
    DESCRIPTION
        "TimeSource 0xFE: Designated for assignment by alternate PTP
        Profiles"
    REFERENCE    "IEEE 1588-2019: clause 7.6.2.8"
    ::= { ieee1588BaseEnumTimeSource 254 }

ieee1588Instances OBJECT IDENTIFIER ::= { ieee1588Objects 2 }

ieee1588DefaultDsTable OBJECT-TYPE
    SYNTAX       SEQUENCE OF Ieee1588DefaultDsEntry
    MAX-ACCESS   not-accessible
    STATUS       current
    DESCRIPTION
        "The defaultDS data set for a specific PTP Instance."
    REFERENCE    "IEEE 1588-2019: clause 8.2.1"
    ::= { ieee1588Instances 1 }
-- .2.1

ieee1588DefaultDsEntry OBJECT-TYPE
    SYNTAX       Ieee1588DefaultDsEntry
    MAX-ACCESS   not-accessible
    STATUS       current
    DESCRIPTION
        "An Entry representing the defaultDS data set for a specific PTP
        Instance."
    INDEX        {
        ieee1588InstanceIndex }
    ::= { ieee1588DefaultDsTable 1 }
-- .2.1.1


Ieee1588DefaultDsEntry    ::= SEQUENCE {
        ieee1588DefaultDsTwoStepFlag            TruthValue,
        ieee1588DefaultDsClockIdentity          Ieee1588ClockIdentity,
        ieee1588DefaultDsNumberPorts            Unsigned32,
        ieee1588DefaultDsClockQualityClockClass Ieee1588ClockClass,
        ieee1588DefaultDsClockQualityClockAccuracy
                                             Ieee1588ClockAccuracy,
        ieee1588DefaultDsClockQualityOffsetScaledLogVariance Unsigned32,
        ieee1588DefaultDsPriority1              Unsigned32,
        ieee1588DefaultDsPriority2              Unsigned32,
        ieee1588DefaultDsDomainNumber           Unsigned32,
        ieee1588DefaultDsSlaveOnly              TruthValue,
        ieee1588DefaultDsSdoId                  Unsigned32,
        ieee1588DefaultDsCurrentTimeSecondsField UInteger48,
        ieee1588DefaultDsCurrentTimeNanosecondsField Unsigned32,
        ieee1588DefaultDsInstanceEnable         TruthValue,
        ieee1588DefaultDsExternalPortConfigurationEnabled TruthValue,
        ieee1588DefaultDsMaxStepsRemoved        Unsigned32,
        ieee1588DefaultDsInstanceType           Ieee1588InstanceType
        }

ieee1588DefaultDsTwoStepFlag OBJECT-TYPE
    SYNTAX       TruthValue
    MAX-ACCESS   read-only
    STATUS       deprecated
    DESCRIPTION
        "When set to true, the PTP Instance is two-step, otherwise the
        PTP Instance is one-step. This data set member is no longer
        used. However, the twoStepFlag of the PTP common header is used.
        One step or two step egress behavior is allowed to be specified
        per PTP Port, or per PTP Instance. Management of the one/two
        step egress behavior of a PTP Port is not provided by this
        standard, but can be specified as extensions to the data sets by
        a PTP Profile or a product specification."
    REFERENCE    "IEEE 1588-2019: clause 8.2.1.2.1"
    ::= { ieee1588DefaultDsEntry 2 }
-- .2.1.1.2

ieee1588DefaultDsClockIdentity OBJECT-TYPE
    SYNTAX       Ieee1588ClockIdentity
    MAX-ACCESS   read-only
    STATUS       current
    DESCRIPTION
        "This value indicates the clockIdentity of the PTP Instance."
    REFERENCE    "IEEE 1588-2019: clause 8.2.1.2.2"
    ::= { ieee1588DefaultDsEntry 3 }
-- .2.1.1.3

ieee1588DefaultDsNumberPorts OBJECT-TYPE
    SYNTAX       Unsigned32(0..65535)
    MAX-ACCESS   read-only
    STATUS       current
    DESCRIPTION
        "This value indicates the number of PTP Ports on the PTP
        Instance. For an Ordinary Clock, this value shall be 1."
    REFERENCE    "IEEE 1588-2019: clause 8.2.1.2.3"
    ::= { ieee1588DefaultDsEntry 4 }
-- .2.1.1.4

ieee1588DefaultDsClockQualityClockClass OBJECT-TYPE
    SYNTAX       Ieee1588ClockClass
    MAX-ACCESS   read-write
    STATUS       current
    DESCRIPTION
        "This value indicates the clockClass attribute of an Ordinary
        Clock or Boundary Clock and denotes the traceability,
        synchronization state and expected performance of the time or
        frequency distributed by the Grandmaster PTP Instance. The
        clockClass is one of the attributes that characterizes a PTP
        Instance for the purpose of the Best Master Clock Algorithm
        (BMCA)."
    REFERENCE    "IEEE 1588-2019: clause 8.2.1.3.1.2"
    ::= { ieee1588DefaultDsEntry 5 }
-- .2.1.1.5

ieee1588DefaultDsClockQualityClockAccuracy OBJECT-TYPE
    SYNTAX       Ieee1588ClockAccuracy
    MAX-ACCESS   read-write
    STATUS       current
    DESCRIPTION
        "This value indicates the accuracy of the clock (Local PTP Clock
        of the PTP Instance)."
    REFERENCE    "IEEE 1588-2019: clause 8.2.1.3.1.3"
    ::= { ieee1588DefaultDsEntry 6 }
-- .2.1.1.6

ieee1588DefaultDsClockQualityOffsetScaledLogVariance OBJECT-TYPE
    SYNTAX       Unsigned32(0..65535)
    MAX-ACCESS   read-write
    STATUS       current
    DESCRIPTION
        "This value indicates the stability of the Local PTP Clock of
        the PTP Instance. It provides an estimate of the variations of
        the Local PTP Clock when it is not synchronized to another Local
        PTP Clock using the protocol."
    REFERENCE    "IEEE 1588-2019: clause 8.2.1.3.1.4"
    ::= { ieee1588DefaultDsEntry 7 }
-- .2.1.1.7

ieee1588DefaultDsPriority1 OBJECT-TYPE
    SYNTAX       Unsigned32(0..255)
    MAX-ACCESS   read-write
    STATUS       current
    DESCRIPTION
        "This value indicates the priority1 of the PTP Instance. Lower
        values take precedence."
    REFERENCE    "IEEE 1588-2019: clause 8.2.1.4.1"
    ::= { ieee1588DefaultDsEntry 8 }
-- .2.1.1.8

ieee1588DefaultDsPriority2 OBJECT-TYPE
    SYNTAX       Unsigned32(0..255)
    MAX-ACCESS   read-write
    STATUS       current
    DESCRIPTION
        "This value indicates the priority2 of the PTP Instance. Lower
        values take precedence."
    REFERENCE    "IEEE 1588-2019: clause 8.2.1.4.2"
    ::= { ieee1588DefaultDsEntry 9 }
-- .2.1.1.9

ieee1588DefaultDsDomainNumber OBJECT-TYPE
    SYNTAX       Unsigned32(0..255)
    MAX-ACCESS   read-write
    STATUS       current
    DESCRIPTION
        "This value indicates the domainNumber of the PTP Instance.
        A domain consists of one or more PTP Instances communicating
        with each other as defined by the protocol. A domain shall
        define the scope of PTP message communication, state,
        operations, data sets, and timescale. Therefore, each domain
        represents a distinct time.
        Within a PTP Network, a domain is identified by two data set
        members: domainNumber and sdoId. The domainNumber is the primary
        mechanism for end users and system integrators to isolate the
        operation of a PTP Instance from PTP messages used in other
        domains. The value of the domainNumber shall be configurable to
        values permitted in IEEE Std 1588, unless the allowed values are
        further restricted by the applicable PTP Profile."
    REFERENCE    "IEEE 1588-2019: clause 8.2.1.4.3"
    ::= { ieee1588DefaultDsEntry 10 }
-- .2.1.1.10

ieee1588DefaultDsSlaveOnly OBJECT-TYPE
    SYNTAX       TruthValue
    MAX-ACCESS   read-write
    STATUS       current
    DESCRIPTION
        "This value shall be true if the PTP Instance is a slave-only
        PTP Instance (false for non-slave-only).
        The slave-only member can be true for Ordinary Clocks only. When
        slave-only is true, the PTP Instance implements special behavior
        in the context of the state machines that determine port-state."
    REFERENCE    "IEEE 1588-2019: clause 8.2.1.4.4"
    ::= { ieee1588DefaultDsEntry 11 }
-- .2.1.1.11

ieee1588DefaultDsSdoId OBJECT-TYPE
    SYNTAX       Unsigned32(0..4095)
    MAX-ACCESS   read-write
    STATUS       current
    DESCRIPTION
        "This value indicates the sdoId of the PTP Instance.
        A domain consists of one or more PTP Instances communicating
        with each other as defined by the protocol. A domain shall
        define the scope of PTP message communication, state,
        operations, data sets, and timescale. Therefore, each domain
        represents a distinct time.
        Within a PTP Network, a domain is identified by two data set
        members: domainNumber and sdoId. The sdoId of a domain is a
        12-bit integer in the closed range 0 to 4095. The sdoId member
        is the primary mechanism for providing isolation of PTP
        Instances operating a PTP Profile specified by a Standards
        Development Organization (SDO), from other PTP Instances
        operating under a PTP Profile specified by a different SDO."
    REFERENCE    "IEEE 1588-2019: clause 8.2.1.4.5"
    ::= { ieee1588DefaultDsEntry 12 }
-- .2.1.1.12

ieee1588DefaultDsCurrentTimeSecondsField OBJECT-TYPE
    SYNTAX       UInteger48
    UNITS        "seconds"
    MAX-ACCESS   read-write
    STATUS       current
    DESCRIPTION
        "This value represents the integer portion of the timestamp in
        units of seconds, a positive time with respect to the epoch.
        For management read, this member shall return the current value
        of the PTP Instance Time. When management write is supported,
        this member shall set the PTP Instance Time. Time originates in
        the Grandmaster PTP Instance and is distributed by PTP to other
        PTP Instances in the domain.
        NOTE 1 - The time in the Grandmaster PTP Instance is normally
        determined by interacting with a primary reference, e.g., GPS,
        by means outside the scope of this standard.
        NOTE 2 - When this member is used to set time in a PTP Instance
        other than the Grandmaster PTP Instance, the PTP Node can return
        a management error.
        NOTE 3 - If the time is set in a PTP Instance other than the
        Grandmaster PTP Instance, it will be overwritten by the
        operation of the protocol and will therefore exist only as a
        transient."
    REFERENCE    "IEEE 1588-2019: clause 5.3.3, 8.2.1.5.1"
    ::= { ieee1588DefaultDsEntry 13 }
-- .2.1.1.13

ieee1588DefaultDsCurrentTimeNanosecondsField OBJECT-TYPE
    SYNTAX       Unsigned32(0..999999999)
    UNITS        "nanoseconds"
    MAX-ACCESS   read-write
    STATUS       current
    DESCRIPTION
        "This value represents the fractional portion of the timestamp
        in units of nanoseconds, a positive time with respect to the
        epoch. This value is always less than 10^9.
        For management read, this member shall return the current value
        of the PTP Instance Time.
        When management write is supported, this member shall set the
        PTP Instance Time.
        Time originates in the Grandmaster PTP Instance and is
        distributed by PTP to other PTP Instances in the domain.
        NOTE 1 - The time in the Grandmaster PTP Instance is normally
        determined by interacting with a primary reference, e.g., GPS,
        by means outside the scope of this standard.
        NOTE 2 - When this member is used to set time in a PTP Instance
        other than the Grandmaster PTP Instance, the PTP Node can return
        a management error.
        NOTE 3 - If the time is set in a PTP Instance other than the
        Grandmaster PTP Instance, it will be overwritten by the
        operation of the protocol and will therefore exist only as a
        transient."
    REFERENCE    "IEEE 1588-2019: clause 5.3.3, 8.2.1.5.1"
    ::= { ieee1588DefaultDsEntry 14 }
-- .2.1.1.14

ieee1588DefaultDsInstanceEnable OBJECT-TYPE
    SYNTAX       TruthValue
    MAX-ACCESS   read-write
    STATUS       current
    DESCRIPTION
        "This value indicates if the PTP Instance is enabled for PTP
        operation. When management write is supported:
        - Write of the value true shall cause the PTP Instance to
        initialize, only if the value was previously false.
        - Write of the value false shall immediately disable operation
        of the PTP Instance (i.e. analogous to power off).
        If this OID is not supported, the PTP Instance shall be
        specified-by-design to be enabled (true)."
    REFERENCE    "IEEE 1588-2019: clause 8.2.1.5.2"
    ::= { ieee1588DefaultDsEntry 15 }
-- .2.1.1.15

ieee1588DefaultDsExternalPortConfigurationEnabled OBJECT-TYPE
    SYNTAX       TruthValue
    MAX-ACCESS   read-write
    STATUS       current
    DESCRIPTION
        "This value determines whether the external port configuration
        option is in the disabled state (false) or enabled state (true).
        When this value is false, each PTP Port's state is determined by
        PTP state machines, including the Best Master Clock Algorithm
        (BMCA). When this value is true, each PTP Port's state is
        configured externally, and PTP state machines are effectively
        disabled. External configuration of PTP Port state can be
        accomplished using the
        ieee1588ExternalPortConfigurationPortDsDesiredState member of
        the PTP Port."
    REFERENCE    "IEEE 1588-2019: clause 8.2.1.5.3"
    ::= { ieee1588DefaultDsEntry 16 }
-- .2.1.1.16

ieee1588DefaultDsMaxStepsRemoved OBJECT-TYPE
    SYNTAX       Unsigned32(0..255)
    MAX-ACCESS   read-write
    STATUS       current
    DESCRIPTION
        "The maximum value of stepsRemoved that qualifies an Announce
        message for consideration by the Best Master Clock Algorithm
        (BMCA). If the value of stepsRemoved of an Announce message is
        greater than or equal to the value of this max-steps-removed
        value, the Announce message is not considered in the operation
        of the BMCA.
        The value shall be in the closed range 2 to 255."
    REFERENCE    "IEEE 1588-2019: clause 8.2.1.5.4"
    ::= { ieee1588DefaultDsEntry 17 }
-- .2.1.1.17

ieee1588DefaultDsInstanceType OBJECT-TYPE
    SYNTAX       Ieee1588InstanceType
    MAX-ACCESS   read-write
    STATUS       current
    DESCRIPTION
        "This value indicates the type of PTP Instance."
    REFERENCE    "IEEE 1588-2019: clause 8.2.1.5.5"
    ::= { ieee1588DefaultDsEntry 18 }
-- .2.1.1.18

ieee1588CurrentDsTable OBJECT-TYPE
    SYNTAX       SEQUENCE OF Ieee1588CurrentDsEntry
    MAX-ACCESS   not-accessible
    STATUS       current
    DESCRIPTION
        "The currentDS data set for a specific PTP Instance."
    REFERENCE    "IEEE 1588-2019: clause 8.2.2"
    ::= { ieee1588Instances 2 }
-- .2.2

ieee1588CurrentDsEntry OBJECT-TYPE
    SYNTAX       Ieee1588CurrentDsEntry
    MAX-ACCESS   not-accessible
    STATUS       current
    DESCRIPTION
        "An Entry representing currentDS data set in a PTP Instance for
        operation of the protocol."
    INDEX        {
        ieee1588InstanceIndex }
    ::= { ieee1588CurrentDsTable 1 }
-- .2.2.1


Ieee1588CurrentDsEntry    ::= SEQUENCE {
        ieee1588CurrentDsStepsRemoved           Unsigned32,
        ieee1588CurrentDsOffsetFromMaster       Ieee1588TimeInterval,
        ieee1588CurrentDsMeanDelay              Ieee1588TimeInterval,
        ieee1588CurrentDsSyncUncertain          TruthValue
        }

ieee1588CurrentDsStepsRemoved OBJECT-TYPE
    SYNTAX       Unsigned32(0..65535)
    MAX-ACCESS   read-only
    STATUS       current
    DESCRIPTION
        "The number of PTP Communication Paths traversed between this
        PTP Instance and the Grandmaster PTP Instance."
    REFERENCE    "IEEE 1588-2019: clause 8.2.2.2"
    ::= { ieee1588CurrentDsEntry 2 }
-- .2.2.1.2

ieee1588CurrentDsOffsetFromMaster OBJECT-TYPE
    SYNTAX       Ieee1588TimeInterval
    UNITS        "scaled nanoseconds"
    MAX-ACCESS   read-only
    STATUS       current
    DESCRIPTION
        "The current value of the time difference between a Master PTP
        Instance and a Slave PTP Instance as computed by the Slave PTP
        Instance. NOTE - When a PTP Profile requires a Boundary Clock to
        transfer offset information internally from Slave PTP Port to
        Master PTP Port(s), this value effectively returns the offset
        from the Grandmaster PTP Instance."
    REFERENCE    "IEEE 1588-2019: clause 8.2.2.3"
    ::= { ieee1588CurrentDsEntry 3 }
-- .2.2.1.3

ieee1588CurrentDsMeanDelay OBJECT-TYPE
    SYNTAX       Ieee1588TimeInterval
    UNITS        "scaled nanoseconds"
    MAX-ACCESS   read-only
    STATUS       current
    DESCRIPTION
        "The current value of the mean propagation time between a Master
        PTP Instance and a Slave PTP Instance as computed by the Slave
        PTP Instance. If the PTP Instance has no PTP Port in slave or
        uncalibrated state, this returns zero. Otherwise, the slave PTP
        port returns this value depending on its delay-mechanism:
        e2e: mean propagation time over the PTP Communication Path, i.e.
        <meanPathDelay>
        p2p or common_p2p: mean propagation time over the PTP Link, i.e.
        <meanLinkDelay>
        disabled or special: zero"
    REFERENCE    "IEEE 1588-2019: clause 8.2.2.4"
    ::= { ieee1588CurrentDsEntry 4 }
-- .2.2.1.4

ieee1588CurrentDsSyncUncertain OBJECT-TYPE
    SYNTAX       TruthValue
    MAX-ACCESS   read-only
    STATUS       current
    DESCRIPTION
        "This boolean is true when synchronization is uncertain (e.g.,
        not within specification) in either the Parent PTP Port or this
        PTP Instance. The value is copied from a received Announce
        message to transmitted Announce message, such that it reflects
        uncertain synchronization from this PTP Instance to the
        Grandmaster. Performance metrics for determining uncertainty are
        specified by the applicable PTP Profile."
    REFERENCE    "IEEE 1588-2019: clause 8.2.2.5"
    ::= { ieee1588CurrentDsEntry 5 }
-- .2.2.1.5

ieee1588ParentDsTable OBJECT-TYPE
    SYNTAX       SEQUENCE OF Ieee1588ParentDsEntry
    MAX-ACCESS   not-accessible
    STATUS       current
    DESCRIPTION
        "The parentDS data set for a specific PTP Instance."
    REFERENCE    "IEEE 1588-2019: clause 8.2.3"
    ::= { ieee1588Instances 3 }
-- .2.3

ieee1588ParentDsEntry OBJECT-TYPE
    SYNTAX       Ieee1588ParentDsEntry
    MAX-ACCESS   not-accessible
    STATUS       current
    DESCRIPTION
        "An Entry representing data learned from the parent of a PTP
        Instance (i.e. Master PTP Port at the other end of the PTP
        Communication Path)."
    INDEX        {
        ieee1588InstanceIndex }
    ::= { ieee1588ParentDsTable 1 }
-- .2.3.1


Ieee1588ParentDsEntry    ::= SEQUENCE {
        ieee1588ParentDsParentPortIdentityClockIdentity
                                             Ieee1588ClockIdentity,
        ieee1588ParentDsParentPortIdentityPortNumber Unsigned32,
        ieee1588ParentDsParentStats             TruthValue,
        ieee1588ParentDsObservedParentOffsetScaledLogVariance
                                             Unsigned32,
        ieee1588ParentDsObservedParentClockPhaseChangeRate Integer32,
        ieee1588ParentDsGrandmasterIdentity     Ieee1588ClockIdentity,
        ieee1588ParentDsGrandmasterClockQualityClockClass
                                             Ieee1588ClockClass,
        ieee1588ParentDsGrandmasterClockQualityClockAccuracy
                                             Ieee1588ClockAccuracy,
        ieee1588ParentDsGrandmasterClockQualityOffsetScaledLogVariance
                                             Unsigned32,
        ieee1588ParentDsGrandmasterPriority1    Unsigned32,
        ieee1588ParentDsGrandmasterPriority2    Unsigned32,
        ieee1588ParentDsProtocolAddressNetworkProtocol
                                             Ieee1588NetworkProtocol,
        ieee1588ParentDsProtocolAddressAddressLength Unsigned32,
        ieee1588ParentDsProtocolAddressAddressField PhysAddress,
        ieee1588ParentDsSynchronizationUncertain TruthValue
        }

ieee1588ParentDsParentPortIdentityClockIdentity OBJECT-TYPE
    SYNTAX       Ieee1588ClockIdentity
    MAX-ACCESS   read-only
    STATUS       current
    DESCRIPTION
        "The clockIdentity of the Parent PTP Instance that issues the
        Sync messages."
    REFERENCE    "IEEE 1588-2019: clause 8.2.3.2"
    ::= { ieee1588ParentDsEntry 2 }
-- .2.3.1.2

ieee1588ParentDsParentPortIdentityPortNumber OBJECT-TYPE
    SYNTAX       Unsigned32(0..65535)
    MAX-ACCESS   read-only
    STATUS       current
    DESCRIPTION
        "The number of the PTP Port on the parent (master) PTP Instance
        that issues the Sync Messages used in synchronizing the Local
        PTP Clock of this PTP Instance."
    REFERENCE    "IEEE 1588-2019: clause 8.2.3.2"
    ::= { ieee1588ParentDsEntry 3 }
-- .2.3.1.3

ieee1588ParentDsParentStats OBJECT-TYPE
    SYNTAX       TruthValue
    MAX-ACCESS   read-only
    STATUS       current
    DESCRIPTION
        "True if all of the following conditions are satisfied:
        - The PTP Instance has a port in the SLAVE state.
        - The PTP Instance has computed statistically valid estimates of
        the ieee1588ParentDsObservedParentOffsetScaledLogVariance and
        the ieee1588ParentDsObservedParentClockPhaseChangeRate.
        Otherwise false."
    REFERENCE    "IEEE 1588-2019: clause 8.2.3.3"
    ::= { ieee1588ParentDsEntry 4 }
-- .2.3.1.4

ieee1588ParentDsObservedParentOffsetScaledLogVariance OBJECT-TYPE
    SYNTAX       Unsigned32(0..65535)
    MAX-ACCESS   read-only
    STATUS       current
    DESCRIPTION
        "Estimate of the variance of the phase offset of the Local PTP
        Clock of the Parent PTP Instance as measured with respect to the
        Local PTP Clock in the Slave PTP Instance. This measurement is
        optional, but if not made, the value of
        ieee1588ParentDsParentStats shall be false."
    REFERENCE    "IEEE 1588-2019: clause 8.2.3.4"
    ::= { ieee1588ParentDsEntry 5 }
-- .2.3.1.5

ieee1588ParentDsObservedParentClockPhaseChangeRate OBJECT-TYPE
    SYNTAX       Integer32
    MAX-ACCESS   read-only
    STATUS       current
    DESCRIPTION
        "Estimate of the phase change rate of the Local PTP Clock of the
        Parent PTP Instance as measured by the Slave PTP Instance using
        its Local PTP Clock.
        If the estimate exceeds the capacity of its data type, this
        value shall be set to 7FFF FFFF (base 16) or 8000 0000 (base
        16), as appropriate. A positive sign indicates that the phase
        change rate in the Parent PTP Instance is greater than that in
        the Slave PTP Instance. The measurement of this value is
        optional, but if not measured, the value of
        parent-ds/parent-stats shall be false."
    REFERENCE    "IEEE 1588-2019: clause 8.2.3.5"
    ::= { ieee1588ParentDsEntry 6 }
-- .2.3.1.6

ieee1588ParentDsGrandmasterIdentity OBJECT-TYPE
    SYNTAX       Ieee1588ClockIdentity
    MAX-ACCESS   read-only
    STATUS       current
    DESCRIPTION
        "The clockIdentity of the Grandmaster PTP Instance."
    REFERENCE    "IEEE 1588-2019: clause 8.2.3.6"
    ::= { ieee1588ParentDsEntry 7 }
-- .2.3.1.7

ieee1588ParentDsGrandmasterClockQualityClockClass OBJECT-TYPE
    SYNTAX       Ieee1588ClockClass
    MAX-ACCESS   read-only
    STATUS       current
    DESCRIPTION
        "The clockQuality.clockClass attribute of the Grandmaster PTP
        Instance."
    REFERENCE    "IEEE 1588-2019: clause 8.2.3.7"
    ::= { ieee1588ParentDsEntry 8 }
-- .2.3.1.8

ieee1588ParentDsGrandmasterClockQualityClockAccuracy OBJECT-TYPE
    SYNTAX       Ieee1588ClockAccuracy
    MAX-ACCESS   read-only
    STATUS       current
    DESCRIPTION
        "The clockQuality.clockAccuracy attribute of the Grandmaster PTP
        Instance."
    REFERENCE    "IEEE 1588-2019: clause 8.2.3.7"
    ::= { ieee1588ParentDsEntry 9 }
-- .2.3.1.9

ieee1588ParentDsGrandmasterClockQualityOffsetScaledLogVariance
                                                             OBJECT-TYPE
    SYNTAX       Unsigned32(0..65535)
    MAX-ACCESS   read-only
    STATUS       current
    DESCRIPTION
        "The clockQuality.offsetScaledLogVariance attribute of the
        Grandmaster PTP Instance."
    REFERENCE    "IEEE 1588-2019: clause 8.2.3.7"
    ::= { ieee1588ParentDsEntry 10 }
-- .2.3.1.10

ieee1588ParentDsGrandmasterPriority1 OBJECT-TYPE
    SYNTAX       Unsigned32(0..255)
    MAX-ACCESS   read-only
    STATUS       current
    DESCRIPTION
        "The priority1 attribute of the Grandmaster PTP Instance."
    REFERENCE    "IEEE 1588-2019: clause 8.2.3.8"
    ::= { ieee1588ParentDsEntry 11 }
-- .2.3.1.11

ieee1588ParentDsGrandmasterPriority2 OBJECT-TYPE
    SYNTAX       Unsigned32(0..255)
    MAX-ACCESS   read-only
    STATUS       current
    DESCRIPTION
        "The priority2 attribute of the Grandmaster PTP Instance."
    REFERENCE    "IEEE 1588-2019: clause 8.2.3.9"
    ::= { ieee1588ParentDsEntry 12 }
-- .2.3.1.12

ieee1588ParentDsProtocolAddressNetworkProtocol OBJECT-TYPE
    SYNTAX       Ieee1588NetworkProtocol
    MAX-ACCESS   read-only
    STATUS       current
    DESCRIPTION
        "This value indicates the type of the protocol address of the
        PTP Port that issues the Sync messages used in synchronizing
        this PTP Instance."
    REFERENCE    "IEEE 1588-2019: clause 8.2.3.10, 5.3.6"
    ::= { ieee1588ParentDsEntry 13 }
-- .2.3.1.13

ieee1588ParentDsProtocolAddressAddressLength OBJECT-TYPE
    SYNTAX       Unsigned32(1..16)
    UNITS        "octets"
    MAX-ACCESS   read-only
    STATUS       current
    DESCRIPTION
        "This value indicates the length in Octets of the address of the
        PTP Port that issues the Sync messages used in synchronizing
        this PTP Instance."
    REFERENCE    "IEEE 1588-2019: clause 8.2.3.10, 5.3.6"
    ::= { ieee1588ParentDsEntry 14 }
-- .2.3.1.14

ieee1588ParentDsProtocolAddressAddressField OBJECT-TYPE
    SYNTAX       PhysAddress(SIZE (1..16))
    MAX-ACCESS   read-only
    STATUS       current
    DESCRIPTION
        "This value indicates the address of the PTP Port that issues
        the Sync messages used in synchronizing this PTP Instance."
    REFERENCE    "IEEE 1588-2019: clause 8.2.3.10, 5.3.6"
    ::= { ieee1588ParentDsEntry 15 }
-- .2.3.1.15

ieee1588ParentDsSynchronizationUncertain OBJECT-TYPE
    SYNTAX       TruthValue
    MAX-ACCESS   read-only
    STATUS       current
    DESCRIPTION
        "This boolean is true when synchronization is uncertain in the
        Parent PTP Port."
    REFERENCE    "IEEE 1588-2019: clause 8.2.3.11"
    ::= { ieee1588ParentDsEntry 16 }
-- .2.3.1.16

ieee1588TimePropertiesDsTable OBJECT-TYPE
    SYNTAX       SEQUENCE OF Ieee1588TimePropertiesDsEntry
    MAX-ACCESS   not-accessible
    STATUS       current
    DESCRIPTION
        "The timePropertiesDS data set for a specific PTP Instance."
    REFERENCE    "IEEE 1588-2019: clause 8.2.4"
    ::= { ieee1588Instances 4 }
-- .2.4

ieee1588TimePropertiesDsEntry OBJECT-TYPE
    SYNTAX       Ieee1588TimePropertiesDsEntry
    MAX-ACCESS   not-accessible
    STATUS       current
    DESCRIPTION
        "An Entry representing data learned from the current Grandmaster
        PTP Instance."
    INDEX        {
        ieee1588InstanceIndex }
    ::= { ieee1588TimePropertiesDsTable 1 }
-- .2.4.1


Ieee1588TimePropertiesDsEntry    ::= SEQUENCE {
        ieee1588TimePropertiesDsCurrentUtcOffset Integer32,
        ieee1588TimePropertiesDsCurrentUtcOffsetValid TruthValue,
        ieee1588TimePropertiesDsLeap59          TruthValue,
        ieee1588TimePropertiesDsLeap61          TruthValue,
        ieee1588TimePropertiesDsTimeTraceable   TruthValue,
        ieee1588TimePropertiesDsFrequencyTraceable TruthValue,
        ieee1588TimePropertiesDsPtpTimescale    TruthValue,
        ieee1588TimePropertiesDsTimeSource      Ieee1588TimeSource
        }

ieee1588TimePropertiesDsCurrentUtcOffset OBJECT-TYPE
    SYNTAX       Integer32(-32768..32767)
    UNITS        "seconds"
    MAX-ACCESS   read-only
    STATUS       current
    DESCRIPTION
        "The leap-seconds value received from the Grandmaster PTP
        Instance. It is specified as <dLS> in the IEEE Std 1588-2019. It
        is the offset between TAI and UTC. The value of <dLS> is derived
        from UTC-TAI (the negative of <dLS>) specified in IERS Bulletin
        C. If ieee1588TimePropertiesDsCurrentUtcOffsetValid is false,
        this value cannot be used to compute UTC."
    REFERENCE    "IEEE 1588-2019: clause 8.2.4.2"
    ::= { ieee1588TimePropertiesDsEntry 2 }
-- .2.4.1.2

ieee1588TimePropertiesDsCurrentUtcOffsetValid OBJECT-TYPE
    SYNTAX       TruthValue
    MAX-ACCESS   read-only
    STATUS       current
    DESCRIPTION
        "This value shall be true if the values of
        ieee1588TimePropertiesDsCurrentUtcOffset,
        ieee1588TimePropertiesDsLeap59, and
        ieee1588TimePropertiesDsLeap61 are known to be correct,
        otherwise it shall be false.
        If ieee1588TimePropertiesDsPtpTimescale is false (ARB
        timescale), this value is false."
    REFERENCE    "IEEE 1588-2019: clause 8.2.4.3"
    ::= { ieee1588TimePropertiesDsEntry 3 }
-- .2.4.1.3

ieee1588TimePropertiesDsLeap59 OBJECT-TYPE
    SYNTAX       TruthValue
    MAX-ACCESS   read-only
    STATUS       current
    DESCRIPTION
        "If the timescale is PTP, a true value shall indicate that the
        last minute of the current UTC day contains 59 seconds. If the
        timescale is not PTP, the value shall be false."
    REFERENCE    "IEEE 1588-2019: clause 8.2.4.4"
    ::= { ieee1588TimePropertiesDsEntry 4 }
-- .2.4.1.4

ieee1588TimePropertiesDsLeap61 OBJECT-TYPE
    SYNTAX       TruthValue
    MAX-ACCESS   read-only
    STATUS       current
    DESCRIPTION
        "If the timescale is PTP, a true value shall indicate that the
        last minute of the current UTC day contains 61 seconds. If the
        timescale is not PTP, the value shall be false."
    REFERENCE    "IEEE 1588-2019: clause 8.2.4.5"
    ::= { ieee1588TimePropertiesDsEntry 5 }
-- .2.4.1.5

ieee1588TimePropertiesDsTimeTraceable OBJECT-TYPE
    SYNTAX       TruthValue
    MAX-ACCESS   read-only
    STATUS       current
    DESCRIPTION
        "This value shall be true if the timescale is traceable to a
        primary reference; otherwise, the value shall be false.
        The uncertainty specifications appropriate to the evaluation of
        whether traceability to a primary reference is achieved should
        be defined in the applicable PTP Profile. In the absence of such
        a definition the value of this field is implementation
        specific."
    REFERENCE    "IEEE 1588-2019: clause 8.2.4.6"
    ::= { ieee1588TimePropertiesDsEntry 6 }
-- .2.4.1.6

ieee1588TimePropertiesDsFrequencyTraceable OBJECT-TYPE
    SYNTAX       TruthValue
    MAX-ACCESS   read-only
    STATUS       current
    DESCRIPTION
        "This value shall be true if the frequency determining the
        timescale is traceable to a primary reference; otherwise, the
        value shall be false.
        The uncertainty specifications appropriate to the evaluation of
        whether traceability to a primary reference is achieved should
        be defined in the applicable PTP Profile. In the absence of such
        a definition the value of this field is implementation
        specific."
    REFERENCE    "IEEE 1588-2019: clause 8.2.4.7"
    ::= { ieee1588TimePropertiesDsEntry 7 }
-- .2.4.1.7

ieee1588TimePropertiesDsPtpTimescale OBJECT-TYPE
    SYNTAX       TruthValue
    MAX-ACCESS   read-only
    STATUS       current
    DESCRIPTION
        "This value is true if the timescale of the Grandmaster PTP
        Instance is PTP, which is the elapsed time since the PTP epoch
        measured using the second defined by International Atomic Time
        (TAI).
        This value is false if the timescale of the Grandmaster PTP
        Instance is ARB, which is the elapsed time since an arbitrary
        epoch."
    REFERENCE    "IEEE 1588-2019: clause 8.2.4.8"
    ::= { ieee1588TimePropertiesDsEntry 8 }
-- .2.4.1.8

ieee1588TimePropertiesDsTimeSource OBJECT-TYPE
    SYNTAX       Ieee1588TimeSource
    MAX-ACCESS   read-only
    STATUS       current
    DESCRIPTION
        "The source of time used by the Grandmaster PTP Instance."
    REFERENCE    "IEEE 1588-2019: clause 8.2.4.9"
    ::= { ieee1588TimePropertiesDsEntry 9 }
-- .2.4.1.9

ieee1588DescriptionDsTable OBJECT-TYPE
    SYNTAX       SEQUENCE OF Ieee1588DescriptionDsEntry
    MAX-ACCESS   not-accessible
    STATUS       current
    DESCRIPTION
        "The descriptionDS data set for a specific PTP Instance."
    REFERENCE    "IEEE 1588-2019: clause 8.2.5"
    ::= { ieee1588Instances 5 }
-- .2.5

ieee1588DescriptionDsEntry OBJECT-TYPE
    SYNTAX       Ieee1588DescriptionDsEntry
    MAX-ACCESS   not-accessible
    STATUS       current
    DESCRIPTION
        "An Entry providing descriptive information for a specific PTP
        Instance."
    INDEX        {
        ieee1588InstanceIndex }
    ::= { ieee1588DescriptionDsTable 1 }
-- .2.5.1


Ieee1588DescriptionDsEntry    ::= SEQUENCE {
        ieee1588DescriptionDsManufacturerIdentity PhysAddress,
        ieee1588DescriptionDsProductDescription SnmpAdminString,
        ieee1588DescriptionDsProductRevision    SnmpAdminString,
        ieee1588DescriptionDsUserDescription    SnmpAdminString
        }

ieee1588DescriptionDsManufacturerIdentity OBJECT-TYPE
    SYNTAX       PhysAddress(SIZE (3))
    MAX-ACCESS   read-only
    STATUS       current
    DESCRIPTION
        "This value shall be an OUI or CID owned by the manufacturer of
        the PTP Instance, assigned by the IEEE Registration Authority."
    REFERENCE    "IEEE 1588-2019: clause 8.2.5.2"
    ::= { ieee1588DescriptionDsEntry 2 }
-- .2.5.1.2

ieee1588DescriptionDsProductDescription OBJECT-TYPE
    SYNTAX       SnmpAdminString(SIZE (0..64))
    MAX-ACCESS   read-only
    STATUS       current
    DESCRIPTION
        "This value shall indicate, in order:
        - The name of the manufacturer of the PTP Instance,
        manufacturerName, followed by a semicolon (;)
        - The model number of the PTP Instance, modelNumber, followed by
        a semicolon (;)
        - An identifier of this PTP Instance, instanceIdentifier, such
        as the MAC address or the serial number
        The content and meaning of the manufacturerName, modelNumber,
        and the instanceIdentifier strings are determined by the
        manufacturer of the PTP Instance."
    REFERENCE    "IEEE 1588-2019: clause 8.2.5.3"
    ::= { ieee1588DescriptionDsEntry 3 }
-- .2.5.1.3

ieee1588DescriptionDsProductRevision OBJECT-TYPE
    SYNTAX       SnmpAdminString(SIZE (0..32))
    MAX-ACCESS   read-only
    STATUS       current
    DESCRIPTION
        "This value shall indicate the revisions for PTP Instance's
        hardware (HW), firmware (FW), and software (SW). This
        information shall be semicolon (;) separated text fields in the
        order HW;FW;SW. Non-applicable revisions shall be indicated by a
        text field of zero length."
    REFERENCE    "IEEE 1588-2019: clause 8.2.5.4"
    ::= { ieee1588DescriptionDsEntry 4 }
-- .2.5.1.4

ieee1588DescriptionDsUserDescription OBJECT-TYPE
    SYNTAX       SnmpAdminString(SIZE (0..128))
    MAX-ACCESS   read-write
    STATUS       current
    DESCRIPTION
        "Configurable description of the product's PTP Instance. This
        user-description string should specify, in order:
        - A user-defined name of the PTP Instance, for example,
        Sensor-1, followed by a semicolon (;)
        - A user-defined physical location of the PTP Instance, for
        example, Rack-2 Shelf-3"
    REFERENCE    "IEEE 1588-2019: clause 8.2.5.5"
    ::= { ieee1588DescriptionDsEntry 5 }
-- .2.5.1.5

ieee1588FaultLogDs OBJECT IDENTIFIER ::= { ieee1588Instances 6 }

ieee1588FaultLogDsGeneralTable OBJECT-TYPE
    SYNTAX       SEQUENCE OF Ieee1588FaultLogDsGeneralEntry
    MAX-ACCESS   not-accessible
    STATUS       current
    DESCRIPTION
        "A Table providing PTP Instance specific information in
        faultLogDS data set. Represents an optional mechanism for
        logging of faults that occur in the PTP Instance. If one member
        of ieee1588FaultLogDs group is supported, all members shall be
        supported."
    REFERENCE    "IEEE 1588-2019: clause 8.2.6"
    ::= { ieee1588FaultLogDs 1 }
-- .2.6.1

ieee1588FaultLogDsGeneralEntry OBJECT-TYPE
    SYNTAX       Ieee1588FaultLogDsGeneralEntry
    MAX-ACCESS   not-accessible
    STATUS       current
    DESCRIPTION
        "An Entry providing FaultLog information for a specific PTP
        Instance."
    INDEX        {
        ieee1588InstanceIndex }
    ::= { ieee1588FaultLogDsGeneralTable 1 }
-- .2.6.1.1


Ieee1588FaultLogDsGeneralEntry    ::= SEQUENCE {
        ieee1588FaultLogDsNumberOfFaultRecords  Unsigned32,
        ieee1588FaultLogDsReset                 TruthValue
        }

ieee1588FaultLogDsNumberOfFaultRecords OBJECT-TYPE
    SYNTAX       Unsigned32(0..65535)
    MAX-ACCESS   read-only
    STATUS       current
    DESCRIPTION
        "The number of fault records available in a fault record list
        for a PTP Instance."
    REFERENCE    "IEEE 1588-2019: clause 8.2.6.2"
    ::= { ieee1588FaultLogDsGeneralEntry 2 }
-- .2.6.1.1.2

ieee1588FaultLogDsReset OBJECT-TYPE
    SYNTAX       TruthValue
    MAX-ACCESS   read-write
    STATUS       current
    DESCRIPTION
        "Setting to True causes the contents for the PTP Instance of
        ieee1588FaultLogDsFaultRecordListTable to be cleared, and
        ieee1588FaultLogDsNumberOfFaultRecords to be set to zero."
    REFERENCE    "IEEE 1588-2019: clause 8.2.6.4"
    ::= { ieee1588FaultLogDsGeneralEntry 3 }
-- .2.6.1.1.3

ieee1588FaultLogDsFaultRecordListTable OBJECT-TYPE
    SYNTAX       SEQUENCE OF Ieee1588FaultLogDsFaultRecordListEntry
    MAX-ACCESS   not-accessible
    STATUS       current
    DESCRIPTION
        "A table providing Fault Records from faultLogDS data set for a
        specific PTP Instance. Represents an optional mechanism for
        logging of faults that occur in the PTP Instance. If one member
        of ieee1588FaultLogDs group is supported, all members shall be
        supported."
    REFERENCE    "IEEE 1588-2019: clause 8.2.6.3"
    ::= { ieee1588FaultLogDs 2 }
-- .2.6.2

ieee1588FaultLogDsFaultRecordListEntry OBJECT-TYPE
    SYNTAX       Ieee1588FaultLogDsFaultRecordListEntry
    MAX-ACCESS   not-accessible
    STATUS       current
    DESCRIPTION
        "An Entry representing a fault record in a specific PTP
        Instance."
    INDEX        {
        ieee1588InstanceIndex,
        ieee1588FaultLogDsFaultRecordListIndex }
    ::= { ieee1588FaultLogDsFaultRecordListTable 1 }
-- .2.6.2.1


Ieee1588FaultLogDsFaultRecordListEntry    ::= SEQUENCE {
        ieee1588FaultLogDsFaultRecordListIndex  Unsigned32,
        ieee1588FaultLogDsFaultRecordListFaultTimeSecondsField
                                             UInteger48,
        ieee1588FaultLogDsFaultRecordListFaultTimeNanosecondsField
                                             Unsigned32,
        ieee1588FaultLogDsFaultRecordListSeverityCode
                                             Ieee1588SeverityCode,
        ieee1588FaultLogDsFaultRecordListFaultName SnmpAdminString,
        ieee1588FaultLogDsFaultRecordListFaultValue SnmpAdminString,
        ieee1588FaultLogDsFaultRecordListFaultDescription
                                             SnmpAdminString
        }

ieee1588FaultLogDsFaultRecordListIndex OBJECT-TYPE
    SYNTAX       Unsigned32
    MAX-ACCESS   not-accessible
    STATUS       current
    DESCRIPTION
        "Table Index of a Fault Record in faultLogDS data set for a
        specific PTP Instance."
    ::= { ieee1588FaultLogDsFaultRecordListEntry 2 }
-- .2.6.2.1.2

ieee1588FaultLogDsFaultRecordListFaultTimeSecondsField OBJECT-TYPE
    SYNTAX       UInteger48
    UNITS        "seconds"
    MAX-ACCESS   read-only
    STATUS       current
    DESCRIPTION
        "Time the fault occurred as indicated by the Timestamping Clock
        of the PTP Instance.
        This value represents the integer portion of the timestamp in
        units of seconds, a positive time with respect to the epoch."
    REFERENCE    "IEEE 1588-2019: clause 8.2.6.3, 5.3.3, 5.3.10"
    ::= { ieee1588FaultLogDsFaultRecordListEntry 3 }
-- .2.6.2.1.3

ieee1588FaultLogDsFaultRecordListFaultTimeNanosecondsField OBJECT-TYPE
    SYNTAX       Unsigned32(0..999999999)
    UNITS        "nanoseconds"
    MAX-ACCESS   read-only
    STATUS       current
    DESCRIPTION
        "Time the fault occurred as indicated by the Timestamping Clock
        of the PTP Instance.
        This value represents the fractional portion of the timestamp in
        units of nanoseconds, a positive time with respect to the epoch.
        This value is always less than 10^9."
    REFERENCE    "IEEE 1588-2019: clause 8.2.6.3, 5.3.3, 5.3.10"
    ::= { ieee1588FaultLogDsFaultRecordListEntry 4 }
-- .2.6.2.1.4

ieee1588FaultLogDsFaultRecordListSeverityCode OBJECT-TYPE
    SYNTAX       Ieee1588SeverityCode
    MAX-ACCESS   read-only
    STATUS       current
    DESCRIPTION
        "Severity of the fault."
    REFERENCE    "IEEE 1588-2019: clause 8.2.6.3, 5.3.10"
    ::= { ieee1588FaultLogDsFaultRecordListEntry 5 }
-- .2.6.2.1.5

ieee1588FaultLogDsFaultRecordListFaultName OBJECT-TYPE
    SYNTAX       SnmpAdminString
    MAX-ACCESS   read-only
    STATUS       current
    DESCRIPTION
        "Name for the fault, unique within the implementation."
    REFERENCE    "IEEE 1588-2019: clause 8.2.6.3, 5.3.10"
    ::= { ieee1588FaultLogDsFaultRecordListEntry 6 }
-- .2.6.2.1.6

ieee1588FaultLogDsFaultRecordListFaultValue OBJECT-TYPE
    SYNTAX       SnmpAdminString
    MAX-ACCESS   read-only
    STATUS       current
    DESCRIPTION
        "Any value that may be associated with the fault that is
        necessary for fault diagnosis."
    REFERENCE    "IEEE 1588-2019: clause 8.2.6.3, 5.3.10"
    ::= { ieee1588FaultLogDsFaultRecordListEntry 7 }
-- .2.6.2.1.7

ieee1588FaultLogDsFaultRecordListFaultDescription OBJECT-TYPE
    SYNTAX       SnmpAdminString
    MAX-ACCESS   read-only
    STATUS       current
    DESCRIPTION
        "Any supplementary description of the fault."
    REFERENCE    "IEEE 1588-2019: clause 8.2.6.3, 5.3.10"
    ::= { ieee1588FaultLogDsFaultRecordListEntry 8 }
-- .2.6.2.1.8

ieee1588NonVolatileStorageDsTable OBJECT-TYPE
    SYNTAX       SEQUENCE OF Ieee1588NonVolatileStorageDsEntry
    MAX-ACCESS   not-accessible
    STATUS       current
    DESCRIPTION
        "The nonVolatileStorageDS data set for a specific PTP Instance."
    REFERENCE    "IEEE 1588-2019: clause 8.2.7.2"
    ::= { ieee1588Instances 7 }
-- .2.7

ieee1588NonVolatileStorageDsEntry OBJECT-TYPE
    SYNTAX       Ieee1588NonVolatileStorageDsEntry
    MAX-ACCESS   not-accessible
    STATUS       current
    DESCRIPTION
        "An Entry providing configuration of nonvolatile storage for a
        specific PTP Instance."
    INDEX        {
        ieee1588InstanceIndex }
    ::= { ieee1588NonVolatileStorageDsTable 1 }
-- .2.7.1


Ieee1588NonVolatileStorageDsEntry    ::= SEQUENCE {
        ieee1588NonVolatileStorageDsReset       TruthValue,
        ieee1588NonVolatileStorageDsSave        TruthValue
        }

ieee1588NonVolatileStorageDsReset OBJECT-TYPE
    SYNTAX       TruthValue
    MAX-ACCESS   read-write
    STATUS       current
    DESCRIPTION
        "When management write is supported, a write of the value True
        shall cause the contents of nonvolatile read-write storage to be
        reset to the applicable dynamic or configurable data set
        initialization values.
        When management write is supported, a write of the value False
        has no effect, and the PTP Instance should return a management
        error. For management read, this member always returns False."
    REFERENCE    "IEEE 1588-2019: clause 8.1.3.4, 8.2.7.2"
    ::= { ieee1588NonVolatileStorageDsEntry 2 }
-- .2.7.1.2

ieee1588NonVolatileStorageDsSave OBJECT-TYPE
    SYNTAX       TruthValue
    MAX-ACCESS   read-write
    STATUS       current
    DESCRIPTION
        "When management write is supported, a write of the value True
        shall cause the current values of the applicable dynamic or
        configurable data set members to be copied into nonvolatile
        read-write storage.
        When management write is supported, a write of the value False
        has no effect, and the PTP Instance should return a management
        error. For management read, this member always returns False."
    REFERENCE    "IEEE 1588-2019: clause 8.1.3.5, 8.2.7.3"
    ::= { ieee1588NonVolatileStorageDsEntry 3 }
-- .2.7.1.3

ieee1588PathTraceDs OBJECT IDENTIFIER ::= { ieee1588Instances 8 }

ieee1588PathTraceDsTable OBJECT-TYPE
    SYNTAX       SEQUENCE OF Ieee1588AlternateTimeOffsetEntry
    MAX-ACCESS   not-accessible
    STATUS       current
    DESCRIPTION
        "The pathTraceDS data set values for a specific PTP Instance."
    REFERENCE    "IEEE 1588-2019: clause 8.2.8, 16.2.2"
    ::= { ieee1588PathTraceDs 1 }
-- .2.8.1

ieee1588PathTraceDsEntry OBJECT-TYPE
    SYNTAX       Ieee1588AlternateTimeOffsetEntry
    MAX-ACCESS   not-accessible
    STATUS       current
    DESCRIPTION
        "An Entry providing data for the optional Path Trace mechanism
        for a specific PTP Instance.."
    INDEX        {
        ieee1588InstanceIndex }
    ::= { ieee1588PathTraceDsTable 1 }
-- .2.8.1.1


Ieee1588AlternateTimeOffsetEntry    ::= SEQUENCE {
        ieee1588PathTraceDsEnable               TruthValue
        }

ieee1588PathTraceDsEnable OBJECT-TYPE
    SYNTAX       TruthValue
    MAX-ACCESS   read-write
    STATUS       current
    DESCRIPTION
        "Allows for enable/disable of the path trace mechanism using
        management. If this value is true, the path trace mechanism
        shall be operational. If this value is false, the path trace
        mechanism shall be inactive."
    REFERENCE    "IEEE 1588-2019: clause 16.2.2.3.1"
    ::= { ieee1588PathTraceDsEntry 2 }
-- .2.8.1.1.2

ieee1588PathTraceDsListTable OBJECT-TYPE
    SYNTAX       SEQUENCE OF Ieee1588PathTraceDsListEntry
    MAX-ACCESS   not-accessible
    STATUS       current
    DESCRIPTION
        "List records of the pathTraceDS data set for a specific PTP
        Instance."
    REFERENCE    "IEEE 1588-2019: clause 8.2.8, 16.2.2"
    ::= { ieee1588PathTraceDs 2 }
-- .2.8.2

ieee1588PathTraceDsListEntry OBJECT-TYPE
    SYNTAX       Ieee1588PathTraceDsListEntry
    MAX-ACCESS   not-accessible
    STATUS       current
    DESCRIPTION
        "An Entry representing a record of a pathTraceDS data set for a
        specific PTP Instance."
    REFERENCE    "IEEE 1588-2019: clause 16.2.2.2"
    INDEX        {
        ieee1588InstanceIndex,
        ieee1588PathTraceDsListIndex }
    ::= { ieee1588PathTraceDsListTable 1 }
-- .2.8.2.1


Ieee1588PathTraceDsListEntry    ::= SEQUENCE {
        ieee1588PathTraceDsListIndex            Unsigned32,
        ieee1588PathTraceDsListClockIdentity    Ieee1588ClockIdentity
        }

ieee1588PathTraceDsListIndex OBJECT-TYPE
    SYNTAX       Unsigned32
    MAX-ACCESS   not-accessible
    STATUS       current
    DESCRIPTION
        "Table index of a record in the list of pathTraceDS data set for
        a specific PTP Instance. The index in the table reflects the
        order of ClockIdentity values in the pathSequence field of the
        PATH_TRACE TLV."
    ::= { ieee1588PathTraceDsListEntry 2 }
-- .2.8.2.1.2

ieee1588PathTraceDsListClockIdentity OBJECT-TYPE
    SYNTAX       Ieee1588ClockIdentity
    MAX-ACCESS   read-only
    STATUS       current
    DESCRIPTION
        "Clock identity value as provided in the PATH_TRACE TLV."
    REFERENCE    "IEEE 1588-2019: clause 16.2.2.2.1"
    ::= { ieee1588PathTraceDsListEntry 3 }
-- .2.8.2.1.3

ieee1588AlternateTimeScaleOffsetDs
                           OBJECT IDENTIFIER ::= { ieee1588Instances 9 }

ieee1588AlternateTimeScaleOffsetDsTable OBJECT-TYPE
    SYNTAX       SEQUENCE OF Ieee1588AlternateTimeScaleOffsetDsEntry
    MAX-ACCESS   not-accessible
    STATUS       current
    DESCRIPTION
        "The alternateTimescaleOffsetDS data set for a specific PTP
        Instance. Provides data for the optional alternate timescale
        offsets mechanism."
    REFERENCE    "IEEE 1588-2019: clause 16.3.4.1"
    ::= { ieee1588AlternateTimeScaleOffsetDs 1 }
-- .2.9.1

ieee1588AlternateTimeScaleOffsetDsEntry OBJECT-TYPE
    SYNTAX       Ieee1588AlternateTimeScaleOffsetDsEntry
    MAX-ACCESS   not-accessible
    STATUS       current
    DESCRIPTION
        "An Entry providing attributes of alternateTimescaleOffsetDS
        data set for a specific PTP Instance."
    INDEX        {
        ieee1588InstanceIndex }
    ::= { ieee1588AlternateTimeScaleOffsetDsTable 1 }
-- .2.9.1.1


Ieee1588AlternateTimeScaleOffsetDsEntry    ::= SEQUENCE {
        ieee1588AlternateTimeScaleOffsetDsMaxKey Unsigned32
        }

ieee1588AlternateTimeScaleOffsetDsMaxKey OBJECT-TYPE
    SYNTAX       Unsigned32(0..255)
    MAX-ACCESS   read-only
    STATUS       current
    DESCRIPTION
        "The value of this field shall indicate the value of the largest
        ieee1588AlternateTimeScaleOffsetDsListKeyField in the
        ieee1588AlternateTimeScaleOffsetDsListTable."
    REFERENCE    "IEEE 1588-2019: clause 16.3.4.3.1"
    ::= { ieee1588AlternateTimeScaleOffsetDsEntry 2 }
-- .2.9.1.1.2

ieee1588AlternateTimeScaleOffsetDsListTable OBJECT-TYPE
    SYNTAX       SEQUENCE OF Ieee1588AlternateTimeScaleOffsetDsListEntry
    MAX-ACCESS   not-accessible
    STATUS       current
    DESCRIPTION
        "List of Alternate Timescales in the alternateTimescaleOffsetDS
        data set for a specific PTP Instance. Elements in the list can
        be created or deleted, if those operations are supported by
        management."
    REFERENCE    "IEEE 1588-2019: clause 16.3.4.2, 16.3.4.4.1"
    ::= { ieee1588AlternateTimeScaleOffsetDs 2 }
-- .2.9.2

ieee1588AlternateTimeScaleOffsetDsListEntry OBJECT-TYPE
    SYNTAX       Ieee1588AlternateTimeScaleOffsetDsListEntry
    MAX-ACCESS   not-accessible
    STATUS       current
    DESCRIPTION
        "An Entry representing a record of an alternateTimeOffsetDS data
        set for a specific PTP Instance."
    INDEX        {
        ieee1588InstanceIndex,
        ieee1588AlternateTimeScaleOffsetDsListIndex }
    ::= { ieee1588AlternateTimeScaleOffsetDsListTable 1 }
-- .2.9.2.1


Ieee1588AlternateTimeScaleOffsetDsListEntry    ::= SEQUENCE {
        ieee1588AlternateTimeScaleOffsetDsListIndex Unsigned32,
        ieee1588AlternateTimeScaleOffsetDsListRowStatus RowStatus,
        ieee1588AlternateTimeScaleOffsetDsListKeyField Unsigned32,
        ieee1588AlternateTimeScaleOffsetDsListEnable TruthValue,
        ieee1588AlternateTimeScaleOffsetDsListCurrentOffset Integer32,
        ieee1588AlternateTimeScaleOffsetDsListJumpSeconds Integer32,
        ieee1588AlternateTimeScaleOffsetDsListTimeOfNextJump UInteger48,
        ieee1588AlternateTimeScaleOffsetDsListDisplayName
                                             SnmpAdminString
        }

ieee1588AlternateTimeScaleOffsetDsListIndex OBJECT-TYPE
    SYNTAX       Unsigned32(0..255)
    MAX-ACCESS   not-accessible
    STATUS       current
    DESCRIPTION
        "Table index of a record in the list of Alternate Timescales for
        a specific PTP Instance."
    ::= { ieee1588AlternateTimeScaleOffsetDsListEntry 2 }
-- .2.9.2.1.2

ieee1588AlternateTimeScaleOffsetDsListRowStatus OBJECT-TYPE
    SYNTAX       RowStatus
    MAX-ACCESS   read-create
    STATUS       current
    DESCRIPTION
        "This object is used to create and delete
        ieee1588AlternateTimeScaleOffsetDsList entries for the PTP
        Instance. All attributes shall be filled on row creation."
    REFERENCE    "IEEE 1588-2019: clause 16.3.4.4.1"
    ::= { ieee1588AlternateTimeScaleOffsetDsListEntry 3 }
-- .2.9.2.1.3

ieee1588AlternateTimeScaleOffsetDsListKeyField OBJECT-TYPE
    SYNTAX       Unsigned32(0..255)
    MAX-ACCESS   read-create
    STATUS       current
    DESCRIPTION
        "Unique identifier of each element in the list."
    REFERENCE    "IEEE 1588-2019: clause 16.3.3.4, 16.3.4.4.1.1"
    ::= { ieee1588AlternateTimeScaleOffsetDsListEntry 4 }
-- .2.9.2.1.4

ieee1588AlternateTimeScaleOffsetDsListEnable OBJECT-TYPE
    SYNTAX       TruthValue
    MAX-ACCESS   read-create
    STATUS       current
    DESCRIPTION
        "If this value is true, the ALTERNATE_TIME_OFFSET_INDICATOR TLV
        for this alternate timescale shall be attached to Announce
        messages. If enable is false, the TLV shall not be attached."
    REFERENCE    "IEEE 1588-2019: clause 16.3.4.4.1.2"
    ::= { ieee1588AlternateTimeScaleOffsetDsListEntry 5 }
-- .2.9.2.1.5

ieee1588AlternateTimeScaleOffsetDsListCurrentOffset OBJECT-TYPE
    SYNTAX       Integer32
    UNITS        "seconds"
    MAX-ACCESS   read-create
    STATUS       current
    DESCRIPTION
        "Offset of the alternate time, in seconds, from PTP Instance
        Time in the Grandmaster PTP Instance."
    REFERENCE    "IEEE 1588-2019: clause 16.3.3.5, 16.3.4.4.1.3"
    ::= { ieee1588AlternateTimeScaleOffsetDsListEntry 6 }
-- .2.9.2.1.6

ieee1588AlternateTimeScaleOffsetDsListJumpSeconds OBJECT-TYPE
    SYNTAX       Integer32
    UNITS        "seconds"
    MAX-ACCESS   read-create
    STATUS       current
    DESCRIPTION
        "Size of the next discontinuity, in seconds, in the alternate
        timescale. A value of zero indicates that no discontinuity is
        expected. A positive value indicates that the discontinuity will
        cause the current-offset of the alternate timescale to
        increase."
    REFERENCE    "IEEE 1588-2019: clause 16.3.3.6, 16.3.4.4.1.4"
    ::= { ieee1588AlternateTimeScaleOffsetDsListEntry 7 }
-- .2.9.2.1.7

ieee1588AlternateTimeScaleOffsetDsListTimeOfNextJump OBJECT-TYPE
    SYNTAX       UInteger48
    UNITS        "seconds"
    MAX-ACCESS   read-create
    STATUS       current
    DESCRIPTION
        "Value of the seconds-field of the transmitting PTP Instance
        Time at the time that the next discontinuity will occur. The
        discontinuity occurs at the start of the second indicated by the
        value of ieee1588AlternateTimeScaleOffsetDsListTimeOfNextJump"
    REFERENCE    "IEEE 1588-2019: clause 16.3.3.7, 16.3.4.4.1.5"
    ::= { ieee1588AlternateTimeScaleOffsetDsListEntry 8 }
-- .2.9.2.1.8

ieee1588AlternateTimeScaleOffsetDsListDisplayName OBJECT-TYPE
    SYNTAX       SnmpAdminString(SIZE (0..10))
    MAX-ACCESS   read-create
    STATUS       current
    DESCRIPTION
        "The value of displayName (text name of the alternate timescale
        in ASCII-8).
        It represents the time zone, e.g. CET;
        a leading character of * indicates that daylight saving time is
        in effect."
    REFERENCE    "IEEE 1588-2019: clause 16.3.3.8, 16.3.4.4.1.6"
    ::= { ieee1588AlternateTimeScaleOffsetDsListEntry 9 }
-- .2.9.2.1.9

ieee1588HoldoverUpgradeDsTable OBJECT-TYPE
    SYNTAX       SEQUENCE OF Ieee1588HoldoverUpgradeDsEntry
    MAX-ACCESS   not-accessible
    STATUS       current
    DESCRIPTION
        "The holdoverUpgradeDS data set. Provides data for the optional
        Holdover Upgrade mechanism."
    REFERENCE    "IEEE 1588-2019: clause 8.2.10, 16.4"
    ::= { ieee1588Instances 10 }
-- .2.10

ieee1588HoldoverUpgradeDsEntry OBJECT-TYPE
    SYNTAX       Ieee1588HoldoverUpgradeDsEntry
    MAX-ACCESS   not-accessible
    STATUS       current
    DESCRIPTION
        "An Entry providing attributes of holdoverUpgradeDS data set for
        a specific PTP Instance."
    INDEX        {
        ieee1588InstanceIndex }
    ::= { ieee1588HoldoverUpgradeDsTable 1 }
-- .2.10.1


Ieee1588HoldoverUpgradeDsEntry    ::= SEQUENCE {
        ieee1588HoldoverUpgradeDsEnable         TruthValue
        }

ieee1588HoldoverUpgradeDsEnable OBJECT-TYPE
    SYNTAX       TruthValue
    MAX-ACCESS   read-write
    STATUS       current
    DESCRIPTION
        "The value provides management access to the optional holdover
        upgrade mechanism. If this value is true, the optional holdover
        upgrade mechanism is enabled; if it is false, the mechanism is
        disabled."
    REFERENCE    "IEEE 1588-2019: clause 8.2.10.1, 16.4.1.1"
    ::= { ieee1588HoldoverUpgradeDsEntry 2 }
-- .2.10.1.2

ieee1588GrandmasterClusterDs
                          OBJECT IDENTIFIER ::= { ieee1588Instances 11 }

ieee1588GrandmasterClusterDsTable OBJECT-TYPE
    SYNTAX       SEQUENCE OF Ieee1588GrandmasterClusterDsEntry
    MAX-ACCESS   not-accessible
    STATUS       current
    DESCRIPTION
        "The grandmasterClusterDS data set for a specific PTP Instance."
    REFERENCE    "IEEE 1588-2019: clause 8.2.11, 17.2.3.1"
    ::= { ieee1588GrandmasterClusterDs 1 }
-- .2.11.1

ieee1588GrandmasterClusterDsEntry OBJECT-TYPE
    SYNTAX       Ieee1588GrandmasterClusterDsEntry
    MAX-ACCESS   not-accessible
    STATUS       current
    DESCRIPTION
        "An Entry providing attributes of grandmasterClusterDS data set
        for a specific PTP Instance."
    INDEX        {
        ieee1588InstanceIndex }
    ::= { ieee1588GrandmasterClusterDsTable 1 }
-- .2.11.1.1


Ieee1588GrandmasterClusterDsEntry    ::= SEQUENCE {
        ieee1588GrandmasterClusterDsMaxTableSize Unsigned32,
        ieee1588GrandmasterClusterDsLogQueryInterval
                                             Ieee1588LogTimeInterval
        }

ieee1588GrandmasterClusterDsMaxTableSize OBJECT-TYPE
    SYNTAX       Unsigned32(0..255)
    MAX-ACCESS   read-only
    STATUS       current
    DESCRIPTION
        "The maximum permitted value of the
        ieee1588GrandmasterClusterDsActualTableSize member in the PTP
        Instance."
    REFERENCE    "IEEE 1588-2019: clause 17.2.3.2.1"
    ::= { ieee1588GrandmasterClusterDsEntry 2 }
-- .2.11.1.1.2

ieee1588GrandmasterClusterDsLogQueryInterval OBJECT-TYPE
    SYNTAX       Ieee1588LogTimeInterval
    UNITS        "log2 seconds"
    MAX-ACCESS   read-write
    STATUS       current
    DESCRIPTION
        "The value of logQueryInterval shall be the logarithm to the
        base 2 of the mean interval in seconds between unicast Announce
        messages from cluster members in the PTP Instance."
    REFERENCE    "IEEE 1588-2019: clause 17.2.3.3.1"
    ::= { ieee1588GrandmasterClusterDsEntry 3 }
-- .2.11.1.1.3

ieee1588GrandmasterClusterDsPortAddressTable OBJECT-TYPE
    SYNTAX      SEQUENCE OF Ieee1588GrandmasterClusterDsPortAddressEntry
    MAX-ACCESS   not-accessible
    STATUS       current
    DESCRIPTION
        "List of Port Addresses of each member of the
        grandmasterClusterDS data set for a specific PTP Instance."
    REFERENCE    "IEEE 1588-2019: clause 17.2.3.3.3"
    ::= { ieee1588GrandmasterClusterDs 2 }
-- .2.11.2

ieee1588GrandmasterClusterDsPortAddressEntry OBJECT-TYPE
    SYNTAX       Ieee1588GrandmasterClusterDsPortAddressEntry
    MAX-ACCESS   not-accessible
    STATUS       current
    DESCRIPTION
        "An Entry representing a Port Addresses of the
        grandmasterClusterDS data set for a specific PTP Instance."
    INDEX        {
        ieee1588InstanceIndex,
        ieee1588GrandmasterClusterDsPortAddressIndex }
    ::= { ieee1588GrandmasterClusterDsPortAddressTable 1 }
-- .2.11.2.1


Ieee1588GrandmasterClusterDsPortAddressEntry    ::= SEQUENCE {
        ieee1588GrandmasterClusterDsPortAddressIndex Unsigned32,
        ieee1588GrandmasterClusterDsPortAddressRowStatus RowStatus,
        ieee1588GrandmasterClusterDsPortAddressNetworkProtocol
                                             Ieee1588NetworkProtocol,
        ieee1588GrandmasterClusterDsPortAddressAddressLength Unsigned32,
        ieee1588GrandmasterClusterDsPortAddressAddressField PhysAddress
        }

ieee1588GrandmasterClusterDsPortAddressIndex OBJECT-TYPE
    SYNTAX       Unsigned32(0..255)
    MAX-ACCESS   not-accessible
    STATUS       current
    DESCRIPTION
        "Table index of a Port Address in grandmasterClusterDS data set
        for a specific PTP Instance."
    ::= { ieee1588GrandmasterClusterDsPortAddressEntry 2 }
-- .2.11.2.1.2

ieee1588GrandmasterClusterDsPortAddressRowStatus OBJECT-TYPE
    SYNTAX       RowStatus
    MAX-ACCESS   read-create
    STATUS       current
    DESCRIPTION
        "This object is used to create and delete
        ieee1588GrandmasterClusterDsPortAddressTable entries for the
        specific PTP Instance. All attributes shall be filled on row
        creation."
    REFERENCE    "IEEE 1588-2019: clause 16.3.4.4.1"
    ::= { ieee1588GrandmasterClusterDsPortAddressEntry 3 }
-- .2.11.2.1.3

ieee1588GrandmasterClusterDsPortAddressNetworkProtocol OBJECT-TYPE
    SYNTAX       Ieee1588NetworkProtocol
    MAX-ACCESS   read-create
    STATUS       current
    DESCRIPTION
        "This value indicates the type of the protocol address which is
        used in grandmaster cluster on a specific PTP Instance."
    REFERENCE    "IEEE 1588-2019: clause 17.2.3.3.3, 5.3.6"
    ::= { ieee1588GrandmasterClusterDsPortAddressEntry 4 }
-- .2.11.2.1.4

ieee1588GrandmasterClusterDsPortAddressAddressLength OBJECT-TYPE
    SYNTAX       Unsigned32(1..16)
    UNITS        "octets"
    MAX-ACCESS   read-create
    STATUS       current
    DESCRIPTION
        "This value indicates the length in Octets of the address of
        protocol address which is used in grandmaster cluster on a
        specific PTP Instance."
    REFERENCE    "IEEE 1588-2019: clause 17.2.3.3.3, 5.3.6"
    ::= { ieee1588GrandmasterClusterDsPortAddressEntry 5 }
-- .2.11.2.1.5

ieee1588GrandmasterClusterDsPortAddressAddressField OBJECT-TYPE
    SYNTAX       PhysAddress(SIZE (1..16))
    MAX-ACCESS   read-create
    STATUS       current
    DESCRIPTION
        "This value indicates the address of the protocol address which
        is used in grandmaster cluster on a specific PTP Instance."
    REFERENCE    "IEEE 1588-2019: clause 17.2.3.3.3, 5.3.6"
    ::= { ieee1588GrandmasterClusterDsPortAddressEntry 6 }
-- .2.11.2.1.6

ieee1588AcceptableMasterTableDs
                          OBJECT IDENTIFIER ::= { ieee1588Instances 12 }

ieee1588AcceptableMasterTableDsTable OBJECT-TYPE
    SYNTAX       SEQUENCE OF Ieee1588AcceptableMasterTableDsEntry
    MAX-ACCESS   not-accessible
    STATUS       current
    DESCRIPTION
        "The acceptableMasterTableDS data set for a specific PTP
        Instance. Provides data for the optional Acceptable Master Table
        mechanism. Mechanism that allows PTP Ports in the SLAVE state to
        be configured to refuse to synchronize to PTP Instances not on
        the Acceptable Master list."
    REFERENCE    "IEEE 1588-2019: clause 17.5.3.1"
    ::= { ieee1588AcceptableMasterTableDs 1 }
-- .2.12.1

ieee1588AcceptableMasterTableDsEntry OBJECT-TYPE
    SYNTAX       Ieee1588AcceptableMasterTableDsEntry
    MAX-ACCESS   not-accessible
    STATUS       current
    DESCRIPTION
        "An Entry providing attributes of acceptableMasterTableDS data
        set for a specific PTP Instance."
    INDEX        {
        ieee1588InstanceIndex }
    ::= { ieee1588AcceptableMasterTableDsTable 1 }
-- .2.12.1.1


Ieee1588AcceptableMasterTableDsEntry    ::= SEQUENCE {
        ieee1588AcceptableMasterTableDsMaxTableSize Unsigned32
        }

ieee1588AcceptableMasterTableDsMaxTableSize OBJECT-TYPE
    SYNTAX       Unsigned32(0..65535)
    MAX-ACCESS   read-only
    STATUS       current
    DESCRIPTION
        "The maximum permitted size of the
        ieee1588AcceptableMasterTableDsListTable."
    REFERENCE    "IEEE 1588-2019: clause 17.5.3.1, 17.5.3.3.1"
    ::= { ieee1588AcceptableMasterTableDsEntry 2 }
-- .2.12.1.1.2

ieee1588AcceptableMasterTableDsListTable OBJECT-TYPE
    SYNTAX       SEQUENCE OF Ieee1588AcceptableMasterTableDsListEntry
    MAX-ACCESS   not-accessible
    STATUS       current
    DESCRIPTION
        "List of Acceptable Masters in the PTP Instance. Elements in the
        list can be created or deleted, if those operations are
        supported by management."
    REFERENCE    "IEEE 1588-2019: clause 8.2.12, 17.5.3.4.2"
    ::= { ieee1588AcceptableMasterTableDs 2 }
-- .2.12.2

ieee1588AcceptableMasterTableDsListEntry OBJECT-TYPE
    SYNTAX       Ieee1588AcceptableMasterTableDsListEntry
    MAX-ACCESS   not-accessible
    STATUS       current
    DESCRIPTION
        "An Entry representing an Acceptable Master in the PTP
        Instance."
    INDEX        {
        ieee1588InstanceIndex,
        ieee1588AcceptableMasterTableDsListIndex }
    ::= { ieee1588AcceptableMasterTableDsListTable 1 }
-- .2.12.2.1


Ieee1588AcceptableMasterTableDsListEntry    ::= SEQUENCE {
        ieee1588AcceptableMasterTableDsListIndex Unsigned32,
        ieee1588AcceptableMasterTableDsListRowStatus RowStatus,
        ieee1588AcceptableMasterTableDsListAccPortIdentityClockIdentity
                                             Ieee1588ClockIdentity,
        ieee1588AcceptableMasterTableDsListAccPortIdentityPortNumber
                                             Unsigned32,
        ieee1588AcceptableMasterTableDsListAlternatePriority1
                                             Unsigned32
        }

ieee1588AcceptableMasterTableDsListIndex OBJECT-TYPE
    SYNTAX       Unsigned32(0..65535)
    MAX-ACCESS   not-accessible
    STATUS       current
    DESCRIPTION
        "Table index of a record in the list of Acceptable Masters in
        the PTP Instance."
    ::= { ieee1588AcceptableMasterTableDsListEntry 2 }
-- .2.12.2.1.2

ieee1588AcceptableMasterTableDsListRowStatus OBJECT-TYPE
    SYNTAX       RowStatus
    MAX-ACCESS   read-create
    STATUS       current
    DESCRIPTION
        "This object is used to create and delete
        ieee1588AcceptableMasterTableDsListTable entries for the PTP
        Instance. All attributes shall be filled on row creation."
    ::= { ieee1588AcceptableMasterTableDsListEntry 3 }
-- .2.12.2.1.3

ieee1588AcceptableMasterTableDsListAccPortIdentityClockIdentity
                                                             OBJECT-TYPE
    SYNTAX       Ieee1588ClockIdentity
    MAX-ACCESS   read-create
    STATUS       current
    DESCRIPTION
        "The clockIdentity of the Acceptable Master in the PTP
        Instance."
    REFERENCE    "IEEE 1588-2019: clause 17.5.3.2, 17.5.3.4.2"
    ::= { ieee1588AcceptableMasterTableDsListEntry 4 }
-- .2.12.2.1.4

ieee1588AcceptableMasterTableDsListAccPortIdentityPortNumber OBJECT-TYPE
    SYNTAX       Unsigned32(0..65535)
    MAX-ACCESS   read-create
    STATUS       current
    DESCRIPTION
        "The PortNumber of the Acceptable Master in the PTP Instance."
    REFERENCE    "IEEE 1588-2019: clause 17.5.3.2, 17.5.3.4.2"
    ::= { ieee1588AcceptableMasterTableDsListEntry 5 }
-- .2.12.2.1.5

ieee1588AcceptableMasterTableDsListAlternatePriority1 OBJECT-TYPE
    SYNTAX       Unsigned32(0..255)
    MAX-ACCESS   read-create
    STATUS       current
    DESCRIPTION
        "The AlternatePriority1 of the Acceptable Master in the PTP
        Instance."
    REFERENCE    "IEEE 1588-2019: clause 17.5.3.2, 17.5.3.4.2"
    ::= { ieee1588AcceptableMasterTableDsListEntry 6 }
-- .2.12.2.1.6

ieee1588PerfMonDs OBJECT IDENTIFIER ::= { ieee1588Instances 13 }

ieee1588PerfMonDsTable OBJECT-TYPE
    SYNTAX       SEQUENCE OF Ieee1588PerfMonDsEntry
    MAX-ACCESS   not-accessible
    STATUS       current
    DESCRIPTION
        "The performanceMonitoringDS data set for a specific PTP
        Instance. Collection of Performance Monitoring logs that can be
        read using management."
    REFERENCE    "IEEE 1588-2019: clause J.5.1"
    ::= { ieee1588PerfMonDs 1 }
-- .2.13.1

ieee1588PerfMonDsEntry OBJECT-TYPE
    SYNTAX       Ieee1588PerfMonDsEntry
    MAX-ACCESS   not-accessible
    STATUS       current
    DESCRIPTION
        "An Entry providing attributes of performanceMonitoringDS data
        set values for a specific PTP Instance."
    INDEX        {
        ieee1588InstanceIndex }
    ::= { ieee1588PerfMonDsTable 1 }
-- .2.13.1.1


Ieee1588PerfMonDsEntry    ::= SEQUENCE {
        ieee1588PerfMonDsEnable                 TruthValue
        }

ieee1588PerfMonDsEnable OBJECT-TYPE
    SYNTAX       TruthValue
    MAX-ACCESS   read-write
    STATUS       current
    DESCRIPTION
        "Permits management control over the collection of performance
        monitoring data, including ieee1588PerfMonDsRecordListTable (PTP
        Instance), ieee1588PerfMonPortDsRecordListTable and
        ieee1588PerfMonPortDsRecordListPdTable (PTP Port of PTP
        Instance)."
    REFERENCE    "IEEE 1588-2019: clause J.5.1.1"
    ::= { ieee1588PerfMonDsEntry 2 }
-- .2.13.1.1.2

ieee1588PerfMonDsRecordListTable OBJECT-TYPE
    SYNTAX       SEQUENCE OF Ieee1588PerfMonDsRecordListEntry
    MAX-ACCESS   not-accessible
    STATUS       current
    DESCRIPTION
        "List performance monitoring records of performanceMonitoringDS
        data set for a specific PTP Instance. Elements in the list can
        be added or removed when described entries become available or
        unavailable. The list is organized as follows:
        - 97 15-minute measurement records, the current record at index
        0, followed by the most recent 96 records.
        - 2 24-hour measurement records, the current record at index 97,
        and the previous record at index 98.
        If a record is not implemented for a specific index, management
        does not return the record. For example, if only four 15-minute
        periods are implemented, a management request for non-existing
        record-list returns an error.
        If only some of the data is reported, the same index values are
        used. As an example, if only the 24-hour statistics are
        accessed, the indexes are still 97 and 98.
        If a specific parameter (e.g.
        ieee1588PerfMonDsRecordListMaxMasterSlaveDelay) is not
        implemented, management does not return the parameter (i.e.,
        error). Parameters that are invalid (not measured correctly)
        shall be indicated with one in all bits, except the most
        significant. This represents the largest positive value of
        Ieee1588TimeInterval, indicating a value outside the maximum
        range."
    REFERENCE    "IEEE 1588-2019: clause J.5.1.2"
    ::= { ieee1588PerfMonDs 2 }
-- .2.13.2

ieee1588PerfMonDsRecordListEntry OBJECT-TYPE
    SYNTAX       Ieee1588PerfMonDsRecordListEntry
    MAX-ACCESS   not-accessible
    STATUS       current
    DESCRIPTION
        "An Entry representing a performance monitoring record of a
        performanceMonitoringDS data set for a specific PTP Instance."
    INDEX        {
        ieee1588InstanceIndex,
        ieee1588PerfMonDsRecordListIndex }
    ::= { ieee1588PerfMonDsRecordListTable 1 }
-- .2.13.2.1


Ieee1588PerfMonDsRecordListEntry    ::= SEQUENCE {
        ieee1588PerfMonDsRecordListIndex        Unsigned32,
        ieee1588PerfMonDsRecordListMeasurementValid TruthValue,
        ieee1588PerfMonDsRecordListPeriodComplete TruthValue,
        ieee1588PerfMonDsRecordListPmTime       TimeStamp,
        ieee1588PerfMonDsRecordListAverageMasterSlaveDelay
                                             Ieee1588TimeInterval,
        ieee1588PerfMonDsRecordListMinMasterSlaveDelay
                                             Ieee1588TimeInterval,
        ieee1588PerfMonDsRecordListMaxMasterSlaveDelay
                                             Ieee1588TimeInterval,
        ieee1588PerfMonDsRecordListStdDevMasterSlaveDelay
                                             Ieee1588TimeInterval,
        ieee1588PerfMonDsRecordListAverageSlaveMasterDelay
                                             Ieee1588TimeInterval,
        ieee1588PerfMonDsRecordListMinSlaveMasterDelay
                                             Ieee1588TimeInterval,
        ieee1588PerfMonDsRecordListMaxSlaveMasterDelay
                                             Ieee1588TimeInterval,
        ieee1588PerfMonDsRecordListStdDevSlaveMasterDelay
                                             Ieee1588TimeInterval,
        ieee1588PerfMonDsRecordListAverageMeanPathDelay
                                             Ieee1588TimeInterval,
        ieee1588PerfMonDsRecordListMinMeanPathDelay
                                             Ieee1588TimeInterval,
        ieee1588PerfMonDsRecordListMaxMeanPathDelay
                                             Ieee1588TimeInterval,
        ieee1588PerfMonDsRecordListStdDevMeanPathDelay
                                             Ieee1588TimeInterval,
        ieee1588PerfMonDsRecordListAverageOffsetFromMaster
                                             Ieee1588TimeInterval,
        ieee1588PerfMonDsRecordListMinOffsetFromMaster
                                             Ieee1588TimeInterval,
        ieee1588PerfMonDsRecordListMaxOffsetFromMaster
                                             Ieee1588TimeInterval,
        ieee1588PerfMonDsRecordListStdDevOffsetFromMaster
                                             Ieee1588TimeInterval
        }

ieee1588PerfMonDsRecordListIndex OBJECT-TYPE
    SYNTAX       Unsigned32(0..98)
    MAX-ACCESS   not-accessible
    STATUS       current
    DESCRIPTION
        "Table index of a performance monitoring record in a
        performanceMonitoringDS data set for a specific PTP Instance."
    REFERENCE    "IEEE 1588-2019: clause J.5.1.2"
    ::= { ieee1588PerfMonDsRecordListEntry 2 }
-- .2.13.2.1.2

ieee1588PerfMonDsRecordListMeasurementValid OBJECT-TYPE
    SYNTAX       TruthValue
    MAX-ACCESS   read-only
    STATUS       current
    DESCRIPTION
        "This flag shall indicate the data can be correctly interpreted.
        Validity is implementation specific and may be defined in a PTP
        Profile. If for some periods the data is not valid for part of
        the data collection interval (e.g. the clock is not locked), a
        specific implementation can report the statistics only for valid
        data and with measurement-valid true. This flag applies to all
        parameters for a given measurement period, including PTP Port
        and Link Port related for specific PTP Instance."
    REFERENCE    "IEEE 1588-2019: clause J.4.1, J.5.1.2"
    ::= { ieee1588PerfMonDsRecordListEntry 3 }
-- .2.13.2.1.3

ieee1588PerfMonDsRecordListPeriodComplete OBJECT-TYPE
    SYNTAX       TruthValue
    MAX-ACCESS   read-only
    STATUS       current
    DESCRIPTION
        "The value specifies that measurements were performed during the
        entire period. For the current 15 min and 24 h period this value
        is false. This flag applies to all parameters for a given
        measurement period, including PTP Port and Link Port related for
        specific PTP Instance."
    REFERENCE    "IEEE 1588-2019: clause J.4.1, J.5.1.2"
    ::= { ieee1588PerfMonDsRecordListEntry 4 }
-- .2.13.2.1.4

ieee1588PerfMonDsRecordListPmTime OBJECT-TYPE
    SYNTAX       TimeStamp
    MAX-ACCESS   read-only
    STATUS       current
    DESCRIPTION
        "This value indicates the time of the beginning of the
        measurement period for specific PTP Instance."
    REFERENCE    "IEEE 1588-2019: clause J.4.1, J.5.1.2"
    ::= { ieee1588PerfMonDsRecordListEntry 5 }
-- .2.13.2.1.5

ieee1588PerfMonDsRecordListAverageMasterSlaveDelay OBJECT-TYPE
    SYNTAX       Ieee1588TimeInterval
    UNITS        "scaled nanoseconds"
    MAX-ACCESS   read-only
    STATUS       current
    DESCRIPTION
        "Average of the MasterSlaveDelay for 15 min or 24 h interval for
        specific PTP Instance."
    REFERENCE    "IEEE 1588-2019: clause J.2, J.5.1.2"
    ::= { ieee1588PerfMonDsRecordListEntry 6 }
-- .2.13.2.1.6

ieee1588PerfMonDsRecordListMinMasterSlaveDelay OBJECT-TYPE
    SYNTAX       Ieee1588TimeInterval
    UNITS        "scaled nanoseconds"
    MAX-ACCESS   read-only
    STATUS       current
    DESCRIPTION
        "Minimum of the MasterSlaveDelay for 15 min or 24 h interval for
        specific PTP Instance."
    REFERENCE    "IEEE 1588-2019: clause J.2, J.5.1.2"
    ::= { ieee1588PerfMonDsRecordListEntry 7 }
-- .2.13.2.1.7

ieee1588PerfMonDsRecordListMaxMasterSlaveDelay OBJECT-TYPE
    SYNTAX       Ieee1588TimeInterval
    UNITS        "scaled nanoseconds"
    MAX-ACCESS   read-only
    STATUS       current
    DESCRIPTION
        "Maximum of the MasterSlaveDelay for 15 min or 24 h interval for
        specific PTP Instance."
    REFERENCE    "IEEE 1588-2019: clause J.2, J.5.1.2"
    ::= { ieee1588PerfMonDsRecordListEntry 8 }
-- .2.13.2.1.8

ieee1588PerfMonDsRecordListStdDevMasterSlaveDelay OBJECT-TYPE
    SYNTAX       Ieee1588TimeInterval
    UNITS        "scaled nanoseconds"
    MAX-ACCESS   read-only
    STATUS       current
    DESCRIPTION
        "Standard deviation of the MasterSlaveDelay for 15 min or 24 h
        interval for specific PTP Instance."
    REFERENCE    "IEEE 1588-2019: clause J.2, J.5.1.2"
    ::= { ieee1588PerfMonDsRecordListEntry 9 }
-- .2.13.2.1.9

ieee1588PerfMonDsRecordListAverageSlaveMasterDelay OBJECT-TYPE
    SYNTAX       Ieee1588TimeInterval
    UNITS        "scaled nanoseconds"
    MAX-ACCESS   read-only
    STATUS       current
    DESCRIPTION
        "Average of the SlaveMasterDelay for 15 min or 24 h interval for
        specific PTP Instance."
    REFERENCE    "IEEE 1588-2019: clause J.2, J.5.1.2"
    ::= { ieee1588PerfMonDsRecordListEntry 10 }
-- .2.13.2.1.10

ieee1588PerfMonDsRecordListMinSlaveMasterDelay OBJECT-TYPE
    SYNTAX       Ieee1588TimeInterval
    UNITS        "scaled nanoseconds"
    MAX-ACCESS   read-only
    STATUS       current
    DESCRIPTION
        "Minimum of the SlaveMasterDelay for 15 min or 24 h interval for
        specific PTP Instance."
    REFERENCE    "IEEE 1588-2019: clause J.2, J.5.1.2"
    ::= { ieee1588PerfMonDsRecordListEntry 11 }
-- .2.13.2.1.11

ieee1588PerfMonDsRecordListMaxSlaveMasterDelay OBJECT-TYPE
    SYNTAX       Ieee1588TimeInterval
    UNITS        "scaled nanoseconds"
    MAX-ACCESS   read-only
    STATUS       current
    DESCRIPTION
        "Maximum of the SlaveMasterDelay for 15 min or 24 h interval for
        specific PTP Instance."
    REFERENCE    "IEEE 1588-2019: clause J.2, J.5.1.2"
    ::= { ieee1588PerfMonDsRecordListEntry 12 }
-- .2.13.2.1.12

ieee1588PerfMonDsRecordListStdDevSlaveMasterDelay OBJECT-TYPE
    SYNTAX       Ieee1588TimeInterval
    UNITS        "scaled nanoseconds"
    MAX-ACCESS   read-only
    STATUS       current
    DESCRIPTION
        "Standard deviation of the SlaveMasterDelay for 15 min or 24 h
        interval for specific PTP Instance."
    REFERENCE    "IEEE 1588-2019: clause J.2, J.5.1.2"
    ::= { ieee1588PerfMonDsRecordListEntry 13 }
-- .2.13.2.1.13

ieee1588PerfMonDsRecordListAverageMeanPathDelay OBJECT-TYPE
    SYNTAX       Ieee1588TimeInterval
    UNITS        "scaled nanoseconds"
    MAX-ACCESS   read-only
    STATUS       current
    DESCRIPTION
        "Average of the meanPathDelay for 15 min or 24 h interval for
        specific PTP Instance."
    REFERENCE    "IEEE 1588-2019: clause J.2, J.5.1.2"
    ::= { ieee1588PerfMonDsRecordListEntry 14 }
-- .2.13.2.1.14

ieee1588PerfMonDsRecordListMinMeanPathDelay OBJECT-TYPE
    SYNTAX       Ieee1588TimeInterval
    UNITS        "scaled nanoseconds"
    MAX-ACCESS   read-only
    STATUS       current
    DESCRIPTION
        "Minimum of the meanPathDelay for 15 min or 24 h interval for
        specific PTP Instance."
    REFERENCE    "IEEE 1588-2019: clause J.2, J.5.1.2"
    ::= { ieee1588PerfMonDsRecordListEntry 15 }
-- .2.13.2.1.15

ieee1588PerfMonDsRecordListMaxMeanPathDelay OBJECT-TYPE
    SYNTAX       Ieee1588TimeInterval
    UNITS        "scaled nanoseconds"
    MAX-ACCESS   read-only
    STATUS       current
    DESCRIPTION
        "Maximum of the meanPathDelay for 15 min or 24 h interval for
        specific PTP Instance."
    REFERENCE    "IEEE 1588-2019: clause J.2, J.5.1.2"
    ::= { ieee1588PerfMonDsRecordListEntry 16 }
-- .2.13.2.1.16

ieee1588PerfMonDsRecordListStdDevMeanPathDelay OBJECT-TYPE
    SYNTAX       Ieee1588TimeInterval
    UNITS        "scaled nanoseconds"
    MAX-ACCESS   read-only
    STATUS       current
    DESCRIPTION
        "Standard deviation of the meanPathDelay for 15 min or 24 h
        interval for specific PTP Instance."
    REFERENCE    "IEEE 1588-2019: clause J.2, J.5.1.2"
    ::= { ieee1588PerfMonDsRecordListEntry 17 }
-- .2.13.2.1.17

ieee1588PerfMonDsRecordListAverageOffsetFromMaster OBJECT-TYPE
    SYNTAX       Ieee1588TimeInterval
    UNITS        "scaled nanoseconds"
    MAX-ACCESS   read-only
    STATUS       current
    DESCRIPTION
        "Average of the offsetFromMaster for 15 min or 24 h interval for
        specific PTP Instance."
    REFERENCE    "IEEE 1588-2019: clause J.2, J.5.1.2"
    ::= { ieee1588PerfMonDsRecordListEntry 18 }
-- .2.13.2.1.18

ieee1588PerfMonDsRecordListMinOffsetFromMaster OBJECT-TYPE
    SYNTAX       Ieee1588TimeInterval
    UNITS        "scaled nanoseconds"
    MAX-ACCESS   read-only
    STATUS       current
    DESCRIPTION
        "Minimum of the offsetFromMaster for 15 min or 24 h interval for
        specific PTP Instance."
    REFERENCE    "IEEE 1588-2019: clause J.2, J.5.1.2"
    ::= { ieee1588PerfMonDsRecordListEntry 19 }
-- .2.13.2.1.19

ieee1588PerfMonDsRecordListMaxOffsetFromMaster OBJECT-TYPE
    SYNTAX       Ieee1588TimeInterval
    UNITS        "scaled nanoseconds"
    MAX-ACCESS   read-only
    STATUS       current
    DESCRIPTION
        "Maximum of the offsetFromMaster for 15 min or 24 h interval for
        specific PTP Instance."
    REFERENCE    "IEEE 1588-2019: clause J.2, J.5.1.2"
    ::= { ieee1588PerfMonDsRecordListEntry 20 }
-- .2.13.2.1.20

ieee1588PerfMonDsRecordListStdDevOffsetFromMaster OBJECT-TYPE
    SYNTAX       Ieee1588TimeInterval
    UNITS        "scaled nanoseconds"
    MAX-ACCESS   read-only
    STATUS       current
    DESCRIPTION
        "Standard deviation of the offsetFromMaster for 15 min or 24 h
        interval for specific PTP Instance."
    REFERENCE    "IEEE 1588-2019: clause J.2, J.5.1.2"
    ::= { ieee1588PerfMonDsRecordListEntry 21 }
-- .2.13.2.1.21

ieee1588EnhancedSynchronizationAccuracyMetricsDsTable OBJECT-TYPE
    SYNTAX
       SEQUENCE OF Ieee1588EnhancedSynchronizationAccuracyMetricsDsEntry
    MAX-ACCESS   not-accessible
    STATUS       current
    DESCRIPTION
        "The enhancedSynchronizationAccuracyMetricsDS data set for a
        specific PTP Instance. Provides data for the optional Enhanced
        Synchronization Accuracy Metrics mechanism."
    REFERENCE    "IEEE 1588-2019: clause 8.2.14, 16.12"
    ::= { ieee1588Instances 14 }
-- .2.14

ieee1588EnhancedSynchronizationAccuracyMetricsDsEntry OBJECT-TYPE
    SYNTAX       Ieee1588EnhancedSynchronizationAccuracyMetricsDsEntry
    MAX-ACCESS   not-accessible
    STATUS       current
    DESCRIPTION
        "An Entry providing data for the
        enhancedSynchronizationAccuracyMetricsDS data set for a specific
        PTP Instance."
    INDEX        {
        ieee1588InstanceIndex }
    ::= { ieee1588EnhancedSynchronizationAccuracyMetricsDsTable 1 }
-- .2.14.1


Ieee1588EnhancedSynchronizationAccuracyMetricsDsEntry    ::= SEQUENCE {
        ieee1588EnhancedSynchronizationAccuracyMetricsDsEnable
                                             TruthValue
        }

ieee1588EnhancedSynchronizationAccuracyMetricsDsEnable OBJECT-TYPE
    SYNTAX       TruthValue
    MAX-ACCESS   read-write
    STATUS       current
    DESCRIPTION
        "If the Enhanced Synchronization Accuracy Metrics feature is
        implemented, the value true shall indicate that the feature is
        enabled on the PTP Instance, and the value false shall indicate
        that the option is disabled on the PTP Instance."
    REFERENCE    "IEEE 1588-2019: clause 8.2.14.2"
    ::= { ieee1588EnhancedSynchronizationAccuracyMetricsDsEntry 2 }
-- .2.14.1.2

ieee1588PortList OBJECT IDENTIFIER ::= { ieee1588Instances 15 }

ieee1588PortDsTable OBJECT-TYPE
    SYNTAX       SEQUENCE OF Ieee1588PortDsEntry
    MAX-ACCESS   not-accessible
    STATUS       current
    DESCRIPTION
        "Data set for a specific PTP Port within PTP Instance. While the
        PTP Instance is disabled, it is possible to have zero PTP Ports
        (i.e., ports not yet created). While the PTP Instance is
        enabled, an Ordinary Clock will have one PTP Port, and a
        Boundary Clock or Transparent Clock will have more than one PTP
        Port."
    REFERENCE    "IEEE 1588-2019: clause 8.2.15"
    ::= { ieee1588PortList 1 }
-- .2.15.1

ieee1588PortDsEntry OBJECT-TYPE
    SYNTAX       Ieee1588PortDsEntry
    MAX-ACCESS   not-accessible
    STATUS       current
    DESCRIPTION
        "An Entry providing attributes of portDS data set for a specific
        PTP Port within PTP Instance."
    INDEX        {
        ieee1588InstanceIndex,
        ieee1588PortIndex }
    ::= { ieee1588PortDsTable 1 }
-- .2.15.1.1


Ieee1588PortDsEntry    ::= SEQUENCE {
        ieee1588PortDsPortIdentityClockIdentity Ieee1588ClockIdentity,
        ieee1588PortDsPortIdentityPortNumber    Unsigned32,
        ieee1588PortDsPortState                 Ieee1588PortState,
        ieee1588PortDsLogMinDelayReqInterval    Ieee1588LogTimeInterval,
        ieee1588PortDsMeanLinkDelay             Ieee1588TimeInterval,
        ieee1588PortDsLogAnnounceInterval       Ieee1588LogTimeInterval,
        ieee1588PortDsAnnounceReceiptTimeout    Unsigned32,
        ieee1588PortDsLogSyncInterval           Ieee1588LogTimeInterval,
        ieee1588PortDsDelayMechanism            Ieee1588DelayMechanism,
        ieee1588PortDsLogMinPdelayReqInterval   Ieee1588LogTimeInterval,
        ieee1588PortDsVersionNumber             Unsigned32,
        ieee1588PortDsMinorVersionNumber        Unsigned32,
        ieee1588PortDsDelayAsymmetry            Ieee1588TimeInterval,
        ieee1588PortDsPortEnable                TruthValue,
        ieee1588PortDsMasterOnly                TruthValue
        }

ieee1588PortDsPortIdentityClockIdentity OBJECT-TYPE
    SYNTAX       Ieee1588ClockIdentity
    MAX-ACCESS   read-only
    STATUS       current
    DESCRIPTION
        "The portIdentity.clockIdentity attribute of the PTP Port within
        PTP Instance."
    REFERENCE    "IEEE 1588-2019: clause 8.2.15.2.1"
    ::= { ieee1588PortDsEntry 3 }
-- .2.15.1.1.3

ieee1588PortDsPortIdentityPortNumber OBJECT-TYPE
    SYNTAX       Unsigned32(0..65535)
    MAX-ACCESS   read-only
    STATUS       current
    DESCRIPTION
        "The portIdentity.portNumber attribute of the PTP Port within
        PTP Instance."
    REFERENCE    "IEEE 1588-2019: clause 8.2.15.2.1"
    ::= { ieee1588PortDsEntry 4 }
-- .2.15.1.1.4

ieee1588PortDsPortState OBJECT-TYPE
    SYNTAX       Ieee1588PortState
    MAX-ACCESS   read-only
    STATUS       current
    DESCRIPTION
        "The current state of the protocol engine associated with this
        PTP Port within PTP Instance expressed as Ieee1588PortState."
    REFERENCE    "IEEE 1588-2019: clause 8.2.15.3.1"
    ::= { ieee1588PortDsEntry 5 }
-- .2.15.1.1.5

ieee1588PortDsLogMinDelayReqInterval OBJECT-TYPE
    SYNTAX       Ieee1588LogTimeInterval
    UNITS        "log2 seconds"
    MAX-ACCESS   read-only
    STATUS       current
    DESCRIPTION
        "Logarithm to the base 2 of the minDelayReqInterval, the minimum
        permitted mean time interval between successive Delay_Req
        messages sent by a Slave PTP Instance."
    REFERENCE    "IEEE 1588-2019: clause 8.2.15.3.2, 7.7.2.4"
    ::= { ieee1588PortDsEntry 6 }
-- .2.15.1.1.6

ieee1588PortDsMeanLinkDelay OBJECT-TYPE
    SYNTAX       Ieee1588TimeInterval
    UNITS        "scaled nanoseconds"
    MAX-ACCESS   read-only
    STATUS       current
    DESCRIPTION
        "If the value of the ieee1588PortDsDelayMechanism member is
        peer-to-peer (P2P), an estimate of the current one-way
        propagation delay on the link, i.e., <meanPathDelay>, attached
        to this PTP Port computed using the peer delay mechanism.
        For other values of the ieee1588PortDsDelayMechanism this value
        is zero."
    REFERENCE    "IEEE 1588-2019: clause 8.2.15.3.3"
    ::= { ieee1588PortDsEntry 7 }
-- .2.15.1.1.7

ieee1588PortDsLogAnnounceInterval OBJECT-TYPE
    SYNTAX       Ieee1588LogTimeInterval
    UNITS        "log2 seconds"
    MAX-ACCESS   read-write
    STATUS       current
    DESCRIPTION
        "Logarithm to the base 2 of the mean announceInterval, the time
        interval between successive Announce messages sent by a PTP Port
        within PTP Instance."
    REFERENCE    "IEEE 1588-2019: clause 8.2.15.4.1"
    ::= { ieee1588PortDsEntry 8 }
-- .2.15.1.1.8

ieee1588PortDsAnnounceReceiptTimeout OBJECT-TYPE
    SYNTAX       Unsigned32(0..255)
    UNITS        "log2 intervals"
    MAX-ACCESS   read-write
    STATUS       current
    DESCRIPTION
        "The integral multiple of announceInterval that must pass
        without receipt of an Announce message before the occurrence of
        the event ANNOUNCE_RECEIPT_TIMEOUT_EXPIRES. The range shall be 2
        to 255 subject to further restrictions of the applicable PTP
        Profile. While 2 is permissible, normally the value should be at
        least 3."
    REFERENCE    "IEEE 1588-2019: clause 8.2.15.4.2"
    ::= { ieee1588PortDsEntry 9 }
-- .2.15.1.1.9

ieee1588PortDsLogSyncInterval OBJECT-TYPE
    SYNTAX       Ieee1588LogTimeInterval
    UNITS        "log2 seconds"
    MAX-ACCESS   read-write
    STATUS       current
    DESCRIPTION
        "The logarithm to the base 2 of the mean SyncInterval, the time
        interval between successive Sync messages, when transmitted as
        multicast messages.
        The rates for unicast transmissions are negotiated separately on
        a per PTP Port within PTP Instance basis and are not constrained
        by this object."
    REFERENCE    "IEEE 1588-2019: clause 8.2.15.4.3"
    ::= { ieee1588PortDsEntry 10 }
-- .2.15.1.1.10

ieee1588PortDsDelayMechanism OBJECT-TYPE
    SYNTAX       Ieee1588DelayMechanism
    MAX-ACCESS   read-write
    STATUS       current
    DESCRIPTION
        "The path delay measuring mechanism used by the PTP Port within
        PTP Instance in computing <meanDelay> (propagation delay)."
    REFERENCE    "IEEE 1588-2019: clause 8.2.15.4.4"
    ::= { ieee1588PortDsEntry 11 }
-- .2.15.1.1.11

ieee1588PortDsLogMinPdelayReqInterval OBJECT-TYPE
    SYNTAX       Ieee1588LogTimeInterval
    UNITS        "log2 seconds"
    MAX-ACCESS   read-write
    STATUS       current
    DESCRIPTION
        "Logarithm to the base 2 of the minPdelayReqInterval, the
        minimum permitted mean time interval between successive
        Pdelay_Req messages sent over a PTP Link."
    REFERENCE    "IEEE 1588-2019: clause 8.2.15.4.5"
    ::= { ieee1588PortDsEntry 12 }
-- .2.15.1.1.12

ieee1588PortDsVersionNumber OBJECT-TYPE
    SYNTAX       Unsigned32(0..15)
    MAX-ACCESS   read-write
    STATUS       current
    DESCRIPTION
        "The PTP major version in use on the PTP Port within PTP
        Instance. NOTE - This indicates the version of the IEEE 1588
        standard, and not the version of an applicable PTP Profile. It
        is 2 for IEEE Std 1588-2008 and IEEE Std 1588-2019."
    REFERENCE    "IEEE 1588-2019: clause 8.2.15.4.6"
    ::= { ieee1588PortDsEntry 13 }
-- .2.15.1.1.13

ieee1588PortDsMinorVersionNumber OBJECT-TYPE
    SYNTAX       Unsigned32(0..15)
    MAX-ACCESS   read-write
    STATUS       current
    DESCRIPTION
        "The PTP minor version in use on the PTP Port within PTP
        Instance. NOTE - This indicates the version of the IEEE 1588
        standard, and not the version of an applicable PTP Profile. It
        is 0 for IEEE Std 1588-2008 and 1 for IEEE Std 1588-2019."
    REFERENCE    "IEEE 1588-2019: clause 8.2.15.4.7"
    ::= { ieee1588PortDsEntry 14 }
-- .2.15.1.1.14

ieee1588PortDsDelayAsymmetry OBJECT-TYPE
    SYNTAX       Ieee1588TimeInterval
    UNITS        "scaled nanoseconds"
    MAX-ACCESS   read-write
    STATUS       current
    DESCRIPTION
        "The value of <delayAsymmetry> applicable to the PTP Port within
        PTP Instance, which is the difference in transmission time in
        one direction as compared to the opposite direction."
    REFERENCE    "IEEE 1588-2019: clause 8.2.15.4.8"
    ::= { ieee1588PortDsEntry 15 }
-- .2.15.1.1.15

ieee1588PortDsPortEnable OBJECT-TYPE
    SYNTAX       TruthValue
    MAX-ACCESS   read-write
    STATUS       current
    DESCRIPTION
        "Indicates if the PTP Port within PTP Instance is enabled for
        PTP operation.
        When management write is supported:
        - Write of the value true causes the DESIGNATED_ENABLED event to
        occur, even if the value was previously true.
        - Write of the value false causes the DESIGNATED_DISABLED event
        to occur, even if the value was previously false.
        If this object is not supported, the PTP Port shall be
        specified-by-design to be enabled (true)."
    REFERENCE    "IEEE 1588-2019: clause 8.2.15.5.1"
    ::= { ieee1588PortDsEntry 16 }
-- .2.15.1.1.16

ieee1588PortDsMasterOnly OBJECT-TYPE
    SYNTAX       TruthValue
    MAX-ACCESS   read-write
    STATUS       current
    DESCRIPTION
        "If the value is true, the PTP Port within PTP Instance shall be
        in the IEEE Std 1588 masterOnly mode. If the value is false, the
        PTP Port shall not be in the masterOnly mode. When master-only
        is true, the PTP Port can never enter the slave port-state."
    REFERENCE    "IEEE 1588-2019: clause 8.2.15.5.2"
    ::= { ieee1588PortDsEntry 17 }
-- .2.15.1.1.17

ieee1588TimestampCorrectionPortDsTable OBJECT-TYPE
    SYNTAX       SEQUENCE OF Ieee1588TimestampCorrectionPortDsEntry
    MAX-ACCESS   not-accessible
    STATUS       current
    DESCRIPTION
        "The timestampCorrectionPortDS data set for a specific PTP Port
        within PTP Instance. Provides access to the configurable
        correction of timestamps provided to the PTP protocol."
    REFERENCE    "IEEE 1588-2019: clause 8.2.16.1"
    ::= { ieee1588PortList 2 }
-- .2.15.2

ieee1588TimestampCorrectionPortDsEntry OBJECT-TYPE
    SYNTAX       Ieee1588TimestampCorrectionPortDsEntry
    MAX-ACCESS   not-accessible
    STATUS       current
    DESCRIPTION
        "An Entry providing attributes of timestampCorrectionPortDS data
        set for a specific PTP Port within PTP Instance."
    INDEX        {
        ieee1588InstanceIndex,
        ieee1588PortIndex }
    ::= { ieee1588TimestampCorrectionPortDsTable 1 }
-- .2.15.2.1


Ieee1588TimestampCorrectionPortDsEntry    ::= SEQUENCE {
        ieee1588TimestampCorrectionPortDsEgressLatency
                                             Ieee1588TimeInterval,
        ieee1588TimestampCorrectionPortDsIngressLatency
                                             Ieee1588TimeInterval
        }

ieee1588TimestampCorrectionPortDsEgressLatency OBJECT-TYPE
    SYNTAX       Ieee1588TimeInterval
    UNITS        "scaled nanoseconds"
    MAX-ACCESS   read-write
    STATUS       current
    DESCRIPTION
        "Interval between the <egressProvidedTimestamp> provided for a
        PTP message and the time at which the message timestamp point of
        the PTP message crosses the reference plane."
    REFERENCE    "IEEE 1588-2019: clause 8.2.16.2"
    ::= { ieee1588TimestampCorrectionPortDsEntry 3 }
-- .2.15.2.1.3

ieee1588TimestampCorrectionPortDsIngressLatency OBJECT-TYPE
    SYNTAX       Ieee1588TimeInterval
    UNITS        "scaled nanoseconds"
    MAX-ACCESS   read-write
    STATUS       current
    DESCRIPTION
        "Interval between the time the message timestamp point of an
        ingress PTP message crosses the reference plane and the
        <ingressProvidedTimestamp> provided for the PTP message."
    REFERENCE    "IEEE 1588-2019: clause 8.2.16.3"
    ::= { ieee1588TimestampCorrectionPortDsEntry 4 }
-- .2.15.2.1.4

ieee1588AsymmetryCorrectionPortDsTable OBJECT-TYPE
    SYNTAX       SEQUENCE OF Ieee1588AsymmetryCorrectionPortDsEntry
    MAX-ACCESS   not-accessible
    STATUS       current
    DESCRIPTION
        "The asymmetryCorrectionPortDS data set for a specific PTP Port
        within PTP Instance. Provides access to asymmetry correction
        parameters that are used to compute the value of
        <delayAsymmetry>."
    REFERENCE    "IEEE 1588-2019: clause 8.2.17.1"
    ::= { ieee1588PortList 3 }
-- .2.15.3

ieee1588AsymmetryCorrectionPortDsEntry OBJECT-TYPE
    SYNTAX       Ieee1588AsymmetryCorrectionPortDsEntry
    MAX-ACCESS   not-accessible
    STATUS       current
    DESCRIPTION
        "An Entry providing attributes of asymmetryCorrectionPortDS data
        set for a specific PTP Port within PTP Instance."
    INDEX        {
        ieee1588InstanceIndex,
        ieee1588PortIndex }
    ::= { ieee1588AsymmetryCorrectionPortDsTable 1 }
-- .2.15.3.1


Ieee1588AsymmetryCorrectionPortDsEntry    ::= SEQUENCE {
        ieee1588AsymmetryCorrectionPortDsEnable TruthValue,
        ieee1588AsymmetryCorrectionPortDsConstantAsymmetry
                                             Ieee1588TimeInterval,
        ieee1588AsymmetryCorrectionPortDsScaledDelayCoefficient
                                             Ieee1588RelativeDifference
        }

ieee1588AsymmetryCorrectionPortDsEnable OBJECT-TYPE
    SYNTAX       TruthValue
    MAX-ACCESS   read-write
    STATUS       current
    DESCRIPTION
        "When this value is true, the mechanism to calculate
        <delayAsymmetry> for certain media is enabled on this PTP Port
        within PTP Instance. When false, this mechanism is disabled on
        this PTP Port."
    REFERENCE    "IEEE 1588-2019: clause 8.2.17.4, 16.8"
    ::= { ieee1588AsymmetryCorrectionPortDsEntry 3 }
-- .2.15.3.1.3

ieee1588AsymmetryCorrectionPortDsConstantAsymmetry OBJECT-TYPE
    SYNTAX       Ieee1588TimeInterval
    UNITS        "scaled nanoseconds"
    MAX-ACCESS   read-write
    STATUS       current
    DESCRIPTION
        "Constant asymmetry used to fine adjust the dynamically
        calculated value of <delayAsymmetry>, when the optional
        mechanism of 16.8 to calculate <delayAsymmetry> for certain
        media is enabled."
    REFERENCE    "IEEE 1588-2019: clause 8.2.17.2, 16.8"
    ::= { ieee1588AsymmetryCorrectionPortDsEntry 4 }
-- .2.15.3.1.4

ieee1588AsymmetryCorrectionPortDsScaledDelayCoefficient OBJECT-TYPE
    SYNTAX       Ieee1588RelativeDifference
    MAX-ACCESS   read-write
    STATUS       current
    DESCRIPTION
        "This is the <delayCoefficient> (alpha)."
    REFERENCE    "IEEE 1588-2019: clause 8.2.17.3"
    ::= { ieee1588AsymmetryCorrectionPortDsEntry 5 }
-- .2.15.3.1.5

ieee1588DescriptionPortDsTable OBJECT-TYPE
    SYNTAX       SEQUENCE OF Ieee1588DescriptionPortDsEntry
    MAX-ACCESS   not-accessible
    STATUS       current
    DESCRIPTION
        "The descriptionPortDS data set for a specific PTP Port within
        PTP Instance. Provides descriptive information for the PTP
        Port."
    REFERENCE    "IEEE 1588-2019: clause 8.2.18"
    ::= { ieee1588PortList 4 }
-- .2.15.4

ieee1588DescriptionPortDsEntry OBJECT-TYPE
    SYNTAX       Ieee1588DescriptionPortDsEntry
    MAX-ACCESS   not-accessible
    STATUS       current
    DESCRIPTION
        "An Entry providing attributes of descriptionPortDS data set for
        a specific PTP Port within PTP Instance."
    INDEX        {
        ieee1588InstanceIndex,
        ieee1588PortIndex }
    ::= { ieee1588DescriptionPortDsTable 1 }
-- .2.15.4.1


Ieee1588DescriptionPortDsEntry    ::= SEQUENCE {
        ieee1588DescriptionPortDsProfileIdentifier PhysAddress,
        ieee1588DescriptionPortDsProtocolAddressNetworkProtocol
                                             Ieee1588NetworkProtocol,
        ieee1588DescriptionPortDsProtocolAddressAddressLength
                                             Unsigned32,
        ieee1588DescriptionPortDsProtocolAddressAddressField
                                             PhysAddress
        }

ieee1588DescriptionPortDsProfileIdentifier OBJECT-TYPE
    SYNTAX       PhysAddress(SIZE (6))
    MAX-ACCESS   read-only
    STATUS       current
    DESCRIPTION
        "When profile-identifier is supported, its value shall identify
        the PTP Profile implemented by the PTP Port within PTP Instance,
        using the value assigned by the organization that created the
        PTP Profile. The profile identifier is six octets that identify
        the PTP Profile's organization, profile within the organization,
        and version."
    REFERENCE    "IEEE 1588-2019: clause 8.2.18.2"
    ::= { ieee1588DescriptionPortDsEntry 3 }
-- .2.15.4.1.3

ieee1588DescriptionPortDsProtocolAddressNetworkProtocol OBJECT-TYPE
    SYNTAX       Ieee1588NetworkProtocol
    MAX-ACCESS   read-only
    STATUS       current
    DESCRIPTION
        "This value indicates the type of the protocol address which is
        used as the source address by the network transport protocol for
        this PTP Port."
    REFERENCE    "IEEE 1588-2019: clause 8.2.18.3, 5.3.6"
    ::= { ieee1588DescriptionPortDsEntry 4 }
-- .2.15.4.1.4

ieee1588DescriptionPortDsProtocolAddressAddressLength OBJECT-TYPE
    SYNTAX       Unsigned32(1..16)
    UNITS        "octets"
    MAX-ACCESS   read-only
    STATUS       current
    DESCRIPTION
        "This value indicates the length in Octets of the address of
        protocol address which is used as the source address by the
        network transport protocol for this PTP Port."
    REFERENCE    "IEEE 1588-2019: clause 8.2.18.3, 5.3.6"
    ::= { ieee1588DescriptionPortDsEntry 5 }
-- .2.15.4.1.5

ieee1588DescriptionPortDsProtocolAddressAddressField OBJECT-TYPE
    SYNTAX       PhysAddress(SIZE (1..16))
    MAX-ACCESS   read-only
    STATUS       current
    DESCRIPTION
        "This value indicates the address of the protocol address which
        is used as the source address by the network transport protocol
        for this PTP Port."
    REFERENCE    "IEEE 1588-2019: clause 8.2.18.3, 5.3.6"
    ::= { ieee1588DescriptionPortDsEntry 6 }
-- .2.15.4.1.6

ieee1588UnicastNegotiationPortDsTable OBJECT-TYPE
    SYNTAX       SEQUENCE OF Ieee1588UnicastNegotiationPortDsEntry
    MAX-ACCESS   not-accessible
    STATUS       current
    DESCRIPTION
        "The unicastNegotiationPortDS data set for a specific PTP Port
        within PTP Instance. Provides management access to the optional
        unicast negotiation mechanism."
    REFERENCE    "IEEE 1588-2019: clause 8.2.19"
    ::= { ieee1588PortList 5 }
-- .2.15.5

ieee1588UnicastNegotiationPortDsEntry OBJECT-TYPE
    SYNTAX       Ieee1588UnicastNegotiationPortDsEntry
    MAX-ACCESS   not-accessible
    STATUS       current
    DESCRIPTION
        "An Entry providing attributes of unicastNegotiationPortDS data
        set for a specific PTP Port within PTP Instance."
    INDEX        {
        ieee1588InstanceIndex,
        ieee1588PortIndex }
    ::= { ieee1588UnicastNegotiationPortDsTable 1 }
-- .2.15.5.1


Ieee1588UnicastNegotiationPortDsEntry    ::= SEQUENCE {
        ieee1588UnicastNegotiationPortDsEnable  TruthValue
        }

ieee1588UnicastNegotiationPortDsEnable OBJECT-TYPE
    SYNTAX       TruthValue
    MAX-ACCESS   read-write
    STATUS       current
    DESCRIPTION
        "When this value is false, the unicast negotiation mechanism is
        disabled on this PTP Port within PTP Instance. When true, the
        unicast negotiation mechanism is enabled on this PTP Port."
    REFERENCE    "IEEE 1588-2019: clause 8.2.19.2"
    ::= { ieee1588UnicastNegotiationPortDsEntry 3 }
-- .2.15.5.1.3

ieee1588AlternateMasterPortDsTable OBJECT-TYPE
    SYNTAX       SEQUENCE OF Ieee1588AlternateMasterPortDsEntry
    MAX-ACCESS   not-accessible
    STATUS       current
    DESCRIPTION
        "The alternateMasterPortDS data set for a specific PTP Port
        within PTP Instance. Provides management access to the optional
        alternate master mechanism."
    REFERENCE    "IEEE 1588-2019: clause 8.2.20, 17.3.3"
    ::= { ieee1588PortList 6 }
-- .2.15.6

ieee1588AlternateMasterPortDsEntry OBJECT-TYPE
    SYNTAX       Ieee1588AlternateMasterPortDsEntry
    MAX-ACCESS   not-accessible
    STATUS       current
    DESCRIPTION
        "An Entry providing attributes of alternateMasterPortDS data set
        for a specific PTP Port within PTP Instance."
    INDEX        {
        ieee1588InstanceIndex,
        ieee1588PortIndex }
    ::= { ieee1588AlternateMasterPortDsTable 1 }
-- .2.15.6.1


Ieee1588AlternateMasterPortDsEntry    ::= SEQUENCE {
        ieee1588AlternateMasterPortDsNumberOfAlternateMasters
                                             Unsigned32,
        ieee1588AlternateMasterPortDsTransmitAlternateMulticastSync
                                             TruthValue,
        ieee1588AlternateMasterPortDsLogAlternateMulticastSyncInterval
                                             Ieee1588LogTimeInterval
        }

ieee1588AlternateMasterPortDsNumberOfAlternateMasters OBJECT-TYPE
    SYNTAX       Unsigned32(0..255)
    MAX-ACCESS   read-write
    STATUS       current
    DESCRIPTION
        "Limits the number of PTP Ports that can simultaneously transmit
        messages with the alternate master flag set to TRUE."
    REFERENCE    "IEEE 1588-2019: clause 17.3.3.2.1"
    ::= { ieee1588AlternateMasterPortDsEntry 3 }
-- .2.15.6.1.3

ieee1588AlternateMasterPortDsTransmitAlternateMulticastSync OBJECT-TYPE
    SYNTAX       TruthValue
    MAX-ACCESS   read-write
    STATUS       current
    DESCRIPTION
        "Controls Sync transmission. If true and the PTP Port is
        currently transmitting multicast Announce messages with
        alternateMasterFlag TRUE, the PTP Port shall also transmit
        multicast Sync and, if a two-step PTP Instance, Follow_Up
        messages. Otherwise do not transmit these messages."
    REFERENCE    "IEEE 1588-2019: clause 17.3.3.2.2"
    ::= { ieee1588AlternateMasterPortDsEntry 4 }
-- .2.15.6.1.4

ieee1588AlternateMasterPortDsLogAlternateMulticastSyncInterval
                                                             OBJECT-TYPE
    SYNTAX       Ieee1588LogTimeInterval
    UNITS        "log2 seconds"
    MAX-ACCESS   read-write
    STATUS       current
    DESCRIPTION
        "Logarithm to the base 2 of the mean interval in seconds between
        Sync messages transmitted under the terms of this Alternate
        Masters mechanism."
    REFERENCE    "IEEE 1588-2019: clause 17.3.3.2.3"
    ::= { ieee1588AlternateMasterPortDsEntry 5 }
-- .2.15.6.1.5

ieee1588UnicastDiscoveryPortDs
                            OBJECT IDENTIFIER ::= { ieee1588PortList 7 }

ieee1588UnicastDiscoveryPortDsTable OBJECT-TYPE
    SYNTAX       SEQUENCE OF Ieee1588UnicastDiscoveryPortDsEntry
    MAX-ACCESS   not-accessible
    STATUS       current
    DESCRIPTION
        "The unicastDiscoveryPortDS data set for a specific PTP Port
        within PTP Instance. Provides management access to the optional
        unicast discovery mechanism."
    REFERENCE    "IEEE 1588-2019: clause 17.4.3"
    ::= { ieee1588UnicastDiscoveryPortDs 1 }
-- .2.15.7.1

ieee1588UnicastDiscoveryPortDsEntry OBJECT-TYPE
    SYNTAX       Ieee1588UnicastDiscoveryPortDsEntry
    MAX-ACCESS   not-accessible
    STATUS       current
    DESCRIPTION
        "An Entry providing attributes of unicastDiscoveryPortDS data
        set for a specific PTP Port within PTP Instance."
    INDEX        {
        ieee1588InstanceIndex,
        ieee1588PortIndex }
    ::= { ieee1588UnicastDiscoveryPortDsTable 1 }
-- .2.15.7.1.1


Ieee1588UnicastDiscoveryPortDsEntry    ::= SEQUENCE {
        ieee1588UnicastDiscoveryPortDsMaxTableSize Unsigned32,
        ieee1588UnicastDiscoveryPortDsLogQueryInterval
                                             Ieee1588LogTimeInterval
        }

ieee1588UnicastDiscoveryPortDsMaxTableSize OBJECT-TYPE
    SYNTAX       Unsigned32(0..65535)
    MAX-ACCESS   read-only
    STATUS       current
    DESCRIPTION
        "Maximum number of elements permitted in the
        ieee1588UnicastDiscoveryPortDsPortAddressTable for a specific
        PTP Port within PTP Instance."
    REFERENCE    "IEEE 1588-2019: clause 17.4.3.2.1"
    ::= { ieee1588UnicastDiscoveryPortDsEntry 3 }
-- .2.15.7.1.1.3

ieee1588UnicastDiscoveryPortDsLogQueryInterval OBJECT-TYPE
    SYNTAX       Ieee1588LogTimeInterval
    UNITS        "log2 seconds"
    MAX-ACCESS   read-write
    STATUS       current
    DESCRIPTION
        "Logarithm to the base 2 of the mean interval in seconds between
        requests from a PTP Instance for a unicast Announce message."
    REFERENCE    "IEEE 1588-2019: clause 17.4.3.3.1"
    ::= { ieee1588UnicastDiscoveryPortDsEntry 4 }
-- .2.15.7.1.1.4

ieee1588UnicastDiscoveryPortDsPortAddressTable OBJECT-TYPE
    SYNTAX    SEQUENCE OF Ieee1588UnicastDiscoveryPortDsPortAddressEntry
    MAX-ACCESS   not-accessible
    STATUS       current
    DESCRIPTION
        "Lists protocol address records of the unicastDiscoveryPortDS
        data set for a specific PTP Port within PTP Instance. Elements
        in the list can be created or deleted, if those operations are
        supported by management."
    REFERENCE    "IEEE 1588-2019: clause 17.4.3"
    ::= { ieee1588UnicastDiscoveryPortDs 2 }
-- .2.15.7.2

ieee1588UnicastDiscoveryPortDsPortAddressEntry OBJECT-TYPE
    SYNTAX       Ieee1588UnicastDiscoveryPortDsPortAddressEntry
    MAX-ACCESS   not-accessible
    STATUS       current
    DESCRIPTION
        "An Entry representing a protocol addresses record of a
        unicastDiscoveryPortDS data set for a specific PTP Port within
        PTP Instance."
    INDEX        {
        ieee1588InstanceIndex,
        ieee1588PortIndex,
        ieee1588UnicastDiscoveryPortDsPortAddressIndex }
    ::= { ieee1588UnicastDiscoveryPortDsPortAddressTable 1 }
-- .2.15.7.2.1


Ieee1588UnicastDiscoveryPortDsPortAddressEntry    ::= SEQUENCE {
        ieee1588UnicastDiscoveryPortDsPortAddressIndex Unsigned32,
        ieee1588UnicastDiscoveryPortDsPortRowStatus RowStatus,
        ieee1588UnicastDiscoveryPortDsPortAddressNetworkProtocol
                                             Ieee1588NetworkProtocol,
        ieee1588UnicastDiscoveryPortDsPortAddressAddressLength
                                             Unsigned32,
        ieee1588UnicastDiscoveryPortDsPortAddressAddressField
                                             PhysAddress
        }

ieee1588UnicastDiscoveryPortDsPortAddressIndex OBJECT-TYPE
    SYNTAX       Unsigned32(0..65535)
    MAX-ACCESS   not-accessible
    STATUS       current
    DESCRIPTION
        "Table index of a protocol address in unicastDiscoveryDS data
        set for a specific PTP Port within PTP Instance."
    ::= { ieee1588UnicastDiscoveryPortDsPortAddressEntry 3 }
-- .2.15.7.2.1.3

ieee1588UnicastDiscoveryPortDsPortRowStatus OBJECT-TYPE
    SYNTAX       RowStatus
    MAX-ACCESS   read-create
    STATUS       current
    DESCRIPTION
        "This object is used to create and delete
        ieee1588UnicastDiscoveryPortDsPortAddressTable entries for a
        specific PTP Port within PTP Instance. All attributes shall be
        filled on row creation."
    ::= { ieee1588UnicastDiscoveryPortDsPortAddressEntry 4 }
-- .2.15.7.2.1.4

ieee1588UnicastDiscoveryPortDsPortAddressNetworkProtocol OBJECT-TYPE
    SYNTAX       Ieee1588NetworkProtocol
    MAX-ACCESS   read-create
    STATUS       current
    DESCRIPTION
        "This value indicates the type of the protocol address which is
        used for unicast discovery on specific PTP Port within PTP
        Instance."
    REFERENCE    "IEEE 1588-2019: clause 17.4.3.3.3, 5.3.6"
    ::= { ieee1588UnicastDiscoveryPortDsPortAddressEntry 5 }
-- .2.15.7.2.1.5

ieee1588UnicastDiscoveryPortDsPortAddressAddressLength OBJECT-TYPE
    SYNTAX       Unsigned32(1..16)
    UNITS        "octets"
    MAX-ACCESS   read-create
    STATUS       current
    DESCRIPTION
        "This value indicates the length in Octets of the address of
        protocol address which is used for unicast discovery on specific
        PTP Port within PTP Instance."
    REFERENCE    "IEEE 1588-2019: clause 17.4.3.3.3, 5.3.6"
    ::= { ieee1588UnicastDiscoveryPortDsPortAddressEntry 6 }
-- .2.15.7.2.1.6

ieee1588UnicastDiscoveryPortDsPortAddressAddressField OBJECT-TYPE
    SYNTAX       PhysAddress(SIZE (1..16))
    MAX-ACCESS   read-create
    STATUS       current
    DESCRIPTION
        "This value indicates the address of the protocol address which
        is used for unicast discovery on specific PTP Port within PTP
        Instance."
    REFERENCE    "IEEE 1588-2019: clause 17.4.3.3.3, 5.3.6"
    ::= { ieee1588UnicastDiscoveryPortDsPortAddressEntry 7 }
-- .2.15.7.2.1.7

ieee1588AcceptableMasterPortDsTable OBJECT-TYPE
    SYNTAX       SEQUENCE OF Ieee1588AcceptableMasterPortDsEntry
    MAX-ACCESS   not-accessible
    STATUS       current
    DESCRIPTION
        "The acceptableMasterPortDS data set for a specific PTP Port
        within PTP Instance. Provides data for the optional Acceptable
        Master Table mechanism."
    REFERENCE    "IEEE 1588-2019: clause 17.5"
    ::= { ieee1588PortList 8 }
-- .2.15.8

ieee1588AcceptableMasterPortDsEntry OBJECT-TYPE
    SYNTAX       Ieee1588AcceptableMasterPortDsEntry
    MAX-ACCESS   not-accessible
    STATUS       current
    DESCRIPTION
        "An Entry providing attributes of acceptableMasterPortDS data
        set for a specific PTP Port within PTP Instance."
    INDEX        {
        ieee1588InstanceIndex,
        ieee1588PortIndex }
    ::= { ieee1588AcceptableMasterPortDsTable 1 }
-- .2.15.8.1


Ieee1588AcceptableMasterPortDsEntry    ::= SEQUENCE {
        ieee1588AcceptableMasterPortDsEnable    TruthValue
        }

ieee1588AcceptableMasterPortDsEnable OBJECT-TYPE
    SYNTAX       TruthValue
    MAX-ACCESS   read-write
    STATUS       current
    DESCRIPTION
        "When enable is false, the Acceptable Master table option is not
        used on this PTP Port, and the normal operation of the protocol
        is in effect.
        When enable is true, the Acceptable Master table option is used
        on this PTP Port as specified in the standard."
    REFERENCE    "IEEE 1588-2019: clause 17.5.4.2.1"
    ::= { ieee1588AcceptableMasterPortDsEntry 3 }
-- .2.15.8.1.3

ieee1588L1SyncBasicPortDsTable OBJECT-TYPE
    SYNTAX       SEQUENCE OF Ieee1588L1SyncBasicPortDsEntry
    MAX-ACCESS   not-accessible
    STATUS       current
    DESCRIPTION
        "The L1SyncBasicPortDS data set for a specific PTP Port within
        PTP Instance. Provides data for operation of the optional
        layer-1 based synchronization performance enhancement feature."
    REFERENCE    "IEEE 1588-2019: clause L.5"
    ::= { ieee1588PortList 9 }
-- .2.15.9

ieee1588L1SyncBasicPortDsEntry OBJECT-TYPE
    SYNTAX       Ieee1588L1SyncBasicPortDsEntry
    MAX-ACCESS   not-accessible
    STATUS       current
    DESCRIPTION
        "An Entry providing attributes of L1SyncBasicPortDS data set for
        a specific PTP Port within PTP Instance."
    INDEX        {
        ieee1588InstanceIndex,
        ieee1588PortIndex }
    ::= { ieee1588L1SyncBasicPortDsTable 1 }
-- .2.15.9.1


Ieee1588L1SyncBasicPortDsEntry    ::= SEQUENCE {
        ieee1588L1SyncBasicPortDsL1SyncEnabled  TruthValue,
        ieee1588L1SyncBasicPortDsTxCoherentIsRequired TruthValue,
        ieee1588L1SyncBasicPortDsRxCoherentIsRequired TruthValue,
        ieee1588L1SyncBasicPortDsCongruentIsRequired TruthValue,
        ieee1588L1SyncBasicPortDsOptParamsEnabled TruthValue,
        ieee1588L1SyncBasicPortDsLogL1SyncInterval
                                             Ieee1588LogTimeInterval,
        ieee1588L1SyncBasicPortDsL1SyncReceiptTimeout Unsigned32,
        ieee1588L1SyncBasicPortDsL1SyncLinkAlive TruthValue,
        ieee1588L1SyncBasicPortDsIsTxCoherent   TruthValue,
        ieee1588L1SyncBasicPortDsIsRxCoherent   TruthValue,
        ieee1588L1SyncBasicPortDsIsCongruent    TruthValue,
        ieee1588L1SyncBasicPortDsL1SyncState    Ieee1588L1SyncState,
        ieee1588L1SyncBasicPortDsPeerTxCoherentIsRequired TruthValue,
        ieee1588L1SyncBasicPortDsPeerRxCoherentIsRequired TruthValue,
        ieee1588L1SyncBasicPortDsPeerCongruentIsRequired TruthValue,
        ieee1588L1SyncBasicPortDsPeerIsTxCoherent TruthValue,
        ieee1588L1SyncBasicPortDsPeerIsRxCoherent TruthValue,
        ieee1588L1SyncBasicPortDsPeerIsCongruent TruthValue
        }

ieee1588L1SyncBasicPortDsL1SyncEnabled OBJECT-TYPE
    SYNTAX       TruthValue
    MAX-ACCESS   read-write
    STATUS       current
    DESCRIPTION
        "Specifies whether the L1Sync option is enabled on a specific
        PTP Port within PTP Instance. If enabled is true, then the
        L1Sync message exchange is supported and enabled."
    REFERENCE    "IEEE 1588-2019: clause L.5.2.1, L.4.1"
    ::= { ieee1588L1SyncBasicPortDsEntry 3 }
-- .2.15.9.1.3

ieee1588L1SyncBasicPortDsTxCoherentIsRequired OBJECT-TYPE
    SYNTAX       TruthValue
    MAX-ACCESS   read-write
    STATUS       current
    DESCRIPTION
        "The value specifies the configuration of the L1Sync port within
        PTP Instance and the expected configuration of its peer L1Sync
        port. This configuration indicates whether the L1Sync port is
        required to be a transmit coherent port."
    REFERENCE    "IEEE 1588-2019: clause L.5.2.2, L.4.2"
    ::= { ieee1588L1SyncBasicPortDsEntry 4 }
-- .2.15.9.1.4

ieee1588L1SyncBasicPortDsRxCoherentIsRequired OBJECT-TYPE
    SYNTAX       TruthValue
    MAX-ACCESS   read-write
    STATUS       current
    DESCRIPTION
        "The value specifies the configuration of the L1Sync port within
        PTP Instance and the expected configuration of its peer L1Sync
        port. This configuration indicates whether the L1Sync port is
        required to be a receive coherent port."
    REFERENCE    "IEEE 1588-2019: clause L.5.2.3, L.4.3"
    ::= { ieee1588L1SyncBasicPortDsEntry 5 }
-- .2.15.9.1.5

ieee1588L1SyncBasicPortDsCongruentIsRequired OBJECT-TYPE
    SYNTAX       TruthValue
    MAX-ACCESS   read-write
    STATUS       current
    DESCRIPTION
        "The value specifies the configuration of the L1Sync port within
        PTP Instance and the expected configuration of its peer L1Sync
        port. This configuration indicates whether the L1Sync port is
        required to be a congruent port."
    REFERENCE    "IEEE 1588-2019: clause L.5.2.4, L.4.4"
    ::= { ieee1588L1SyncBasicPortDsEntry 6 }
-- .2.15.9.1.6

ieee1588L1SyncBasicPortDsOptParamsEnabled OBJECT-TYPE
    SYNTAX       TruthValue
    MAX-ACCESS   read-write
    STATUS       current
    DESCRIPTION
        "The value specifies whether the L1Sync port within PTP Instance
        transmitting the L1_SYNC TLV extends L1_SYNC TLV with the
        information about the optional parameters defined in
        IEEE1588-2019 L.8."
    REFERENCE    "IEEE 1588-2019: clause L.5.2.5, L.4.5, L.8"
    ::= { ieee1588L1SyncBasicPortDsEntry 7 }
-- .2.15.9.1.7

ieee1588L1SyncBasicPortDsLogL1SyncInterval OBJECT-TYPE
    SYNTAX       Ieee1588LogTimeInterval
    UNITS        "log2 seconds"
    MAX-ACCESS   read-write
    STATUS       current
    DESCRIPTION
        "The value is the logarithm to the base 2 of the L1SyncInterval
        which specifies the mean time interval between successive
        periodic messages sent by the L1Sync port within PTP Instance
        and carrying the L1_SYNC TLV."
    REFERENCE    "IEEE 1588-2019: clause L.5.2.6, L.4.6"
    ::= { ieee1588L1SyncBasicPortDsEntry 8 }
-- .2.15.9.1.8

ieee1588L1SyncBasicPortDsL1SyncReceiptTimeout OBJECT-TYPE
    SYNTAX       Unsigned32(0..255)
    UNITS        "log2 intervals"
    MAX-ACCESS   read-write
    STATUS       current
    DESCRIPTION
        "The value specifies the number of elapsed L1SyncIntervals that
        must pass without reception of the L1_SYNC TLV before the
        L1_SYNC TLV reception timeout occurs."
    REFERENCE    "IEEE 1588-2019: clause L.5.2.7, L.4.7"
    ::= { ieee1588L1SyncBasicPortDsEntry 9 }
-- .2.15.9.1.9

ieee1588L1SyncBasicPortDsL1SyncLinkAlive OBJECT-TYPE
    SYNTAX       TruthValue
    MAX-ACCESS   read-only
    STATUS       current
    DESCRIPTION
        "True when a L1_SYNC TLV is received at the PTP Port and the PTP
        Port is configured with ieee1588L1SyncBasicPortDsL1SyncEnabled
        True. It is set to false when the L1_SYNC TLV reception timeout
        occurs."
    REFERENCE    "IEEE 1588-2019: clause L.5.3.1"
    ::= { ieee1588L1SyncBasicPortDsEntry 10 }
-- .2.15.9.1.10

ieee1588L1SyncBasicPortDsIsTxCoherent OBJECT-TYPE
    SYNTAX       TruthValue
    MAX-ACCESS   read-only
    STATUS       current
    DESCRIPTION
        "The value shall be set to True when the L1Sync Port is a
        transmit coherent port."
    REFERENCE    "IEEE 1588-2019: clause L.5.3.2, L.2.3"
    ::= { ieee1588L1SyncBasicPortDsEntry 11 }
-- .2.15.9.1.11

ieee1588L1SyncBasicPortDsIsRxCoherent OBJECT-TYPE
    SYNTAX       TruthValue
    MAX-ACCESS   read-only
    STATUS       current
    DESCRIPTION
        "The value shall be set to True when the L1Sync Port is a
        receive coherent port."
    REFERENCE    "IEEE 1588-2019: clause L.5.3.3, L.2.4"
    ::= { ieee1588L1SyncBasicPortDsEntry 12 }
-- .2.15.9.1.12

ieee1588L1SyncBasicPortDsIsCongruent OBJECT-TYPE
    SYNTAX       TruthValue
    MAX-ACCESS   read-only
    STATUS       current
    DESCRIPTION
        "The value shall be set to True when the PTP Port is a congruent
        port."
    REFERENCE    "IEEE 1588-2019: clause L.5.3.4, L.2.5"
    ::= { ieee1588L1SyncBasicPortDsEntry 13 }
-- .2.15.9.1.13

ieee1588L1SyncBasicPortDsL1SyncState OBJECT-TYPE
    SYNTAX       Ieee1588L1SyncState
    MAX-ACCESS   read-only
    STATUS       current
    DESCRIPTION
        "The value shall be the value of the current state of the L1Sync
        state machine associated with this L1Sync port within PTP
        Instance."
    REFERENCE    "IEEE 1588-2019: clause L.5.3.5"
    ::= { ieee1588L1SyncBasicPortDsEntry 14 }
-- .2.15.9.1.14

ieee1588L1SyncBasicPortDsPeerTxCoherentIsRequired OBJECT-TYPE
    SYNTAX       TruthValue
    MAX-ACCESS   read-only
    STATUS       current
    DESCRIPTION
        "Specifies whether the specific L1Sync port within PTP Instance
        is required to be a transmit coherent port by a peer. As
        indicated in the value of the TCR field of the most recently
        received L1_SYNC TLV."
    REFERENCE    "IEEE 1588-2019: clause L.5.3.6"
    ::= { ieee1588L1SyncBasicPortDsEntry 15 }
-- .2.15.9.1.15

ieee1588L1SyncBasicPortDsPeerRxCoherentIsRequired OBJECT-TYPE
    SYNTAX       TruthValue
    MAX-ACCESS   read-only
    STATUS       current
    DESCRIPTION
        "Specifies whether the specific L1Sync port within PTP Instance
        is required to be a receive coherent port by a peer. As
        indicated in the value of the RCR field of the most recently
        received L1_SYNC TLV."
    REFERENCE    "IEEE 1588-2019: clause L.5.3.7"
    ::= { ieee1588L1SyncBasicPortDsEntry 16 }
-- .2.15.9.1.16

ieee1588L1SyncBasicPortDsPeerCongruentIsRequired OBJECT-TYPE
    SYNTAX       TruthValue
    MAX-ACCESS   read-only
    STATUS       current
    DESCRIPTION
        "Specifies whether the specific L1Sync port within PTP Instance
        is required to be a congruent port by a peer. As indicated in
        the value of the CR field of the most recently received L1_SYNC
        TLV."
    REFERENCE    "IEEE 1588-2019: clause L.5.3.8"
    ::= { ieee1588L1SyncBasicPortDsEntry 17 }
-- .2.15.9.1.17

ieee1588L1SyncBasicPortDsPeerIsTxCoherent OBJECT-TYPE
    SYNTAX       TruthValue
    MAX-ACCESS   read-only
    STATUS       current
    DESCRIPTION
        "True when the peer L1Sync port within PTP Instance is a
        transmit coherent port. As indicated in the value of the ITC
        field of the most recently received L1_SYNC TLV."
    REFERENCE    "IEEE 1588-2019: clause L.5.3.9"
    ::= { ieee1588L1SyncBasicPortDsEntry 18 }
-- .2.15.9.1.18

ieee1588L1SyncBasicPortDsPeerIsRxCoherent OBJECT-TYPE
    SYNTAX       TruthValue
    MAX-ACCESS   read-only
    STATUS       current
    DESCRIPTION
        "True when the peer L1Sync port within PTP Instance is a receive
        coherent port. As indicated in the value of the IRC field of the
        most recently received L1_SYNC TLV."
    REFERENCE    "IEEE 1588-2019: clause L.5.3.10"
    ::= { ieee1588L1SyncBasicPortDsEntry 19 }
-- .2.15.9.1.19

ieee1588L1SyncBasicPortDsPeerIsCongruent OBJECT-TYPE
    SYNTAX       TruthValue
    MAX-ACCESS   read-only
    STATUS       current
    DESCRIPTION
        "True when the peer L1Sync port within PTP Instance is a
        congruent port. As indicated in the value of the IC field of the
        most recently received L1_SYNC TLV."
    REFERENCE    "IEEE 1588-2019: clause L.5.3.11"
    ::= { ieee1588L1SyncBasicPortDsEntry 20 }
-- .2.15.9.1.20

ieee1588L1SyncOptParamsPortDsTable OBJECT-TYPE
    SYNTAX       SEQUENCE OF Ieee1588L1SyncOptParamsPortDsEntry
    MAX-ACCESS   not-accessible
    STATUS       current
    DESCRIPTION
        "The L1SyncOptParamsPortDS data set for a specific PTP Port
        within PTP Instance. Provides data for operation of the optional
        layer-1 based synchronization performance enhancement feature.
        This data is optional when the feature is supported."
    REFERENCE    "IEEE 1588-2019: clause L.8.4"
    ::= { ieee1588PortList 10 }
-- .2.15.10

ieee1588L1SyncOptParamsPortDsEntry OBJECT-TYPE
    SYNTAX       Ieee1588L1SyncOptParamsPortDsEntry
    MAX-ACCESS   not-accessible
    STATUS       current
    DESCRIPTION
        "An Entry providing attributes of L1SyncOptParamsPortDS data set
        for a specific PTP Port within PTP Instance."
    INDEX        {
        ieee1588InstanceIndex,
        ieee1588PortIndex }
    ::= { ieee1588L1SyncOptParamsPortDsTable 1 }
-- .2.15.10.1


Ieee1588L1SyncOptParamsPortDsEntry    ::= SEQUENCE {
        ieee1588L1SyncOptParamsPortDsTimestampsCorrectedTx TruthValue,
        ieee1588L1SyncOptParamsPortDsPhaseOffsetTxValid TruthValue,
        ieee1588L1SyncOptParamsPortDsFrequencyOffsetTxValid TruthValue,
        ieee1588L1SyncOptParamsPortDsPhaseOffsetTx Ieee1588TimeInterval,
        ieee1588L1SyncOptParamsPortDsPhaseOffsetTxTsSecondsField
                                             UInteger48,
        ieee1588L1SyncOptParamsPortDsPhaseOffsetTxTsNanosecondsField
                                             Unsigned32,
        ieee1588L1SyncOptParamsPortDsFrequencyOffsetTx
                                             Ieee1588TimeInterval,
        ieee1588L1SyncOptParamsPortDsFrequencyOffsetTxTsSecondsField
                                             UInteger48,
        ieee1588L1SyncOptParamsPortDsFrequencyOffsetTxTsNanosecondsField
                                             Unsigned32
        }

ieee1588L1SyncOptParamsPortDsTimestampsCorrectedTx OBJECT-TYPE
    SYNTAX       TruthValue
    MAX-ACCESS   read-write
    STATUS       current
    DESCRIPTION
        "This value specifies whether the L1Sync port within PTP
        Instance shall correct the transmitted egress timestamps with
        the known value of the phase offset, as indicated in the Link
        Reference Model defined in IEEE1588-2019 L.3."
    REFERENCE    "IEEE 1588-2019: clause L.8.4.2.1"
    ::= { ieee1588L1SyncOptParamsPortDsEntry 3 }
-- .2.15.10.1.3

ieee1588L1SyncOptParamsPortDsPhaseOffsetTxValid OBJECT-TYPE
    SYNTAX       TruthValue
    MAX-ACCESS   read-only
    STATUS       current
    DESCRIPTION
        "The value shall be True if and only if the values of the
        transmission phase offset parameters (provided by
        L1SyncOptParamsPortDsPhaseOffsetTx and
        L1SyncOptParamsPortDsPhaseOffsetTxTimestamp) are valid."
    REFERENCE    "IEEE 1588-2019: clause L.8.4.3.1"
    ::= { ieee1588L1SyncOptParamsPortDsEntry 4 }
-- .2.15.10.1.4

ieee1588L1SyncOptParamsPortDsFrequencyOffsetTxValid OBJECT-TYPE
    SYNTAX       TruthValue
    MAX-ACCESS   read-only
    STATUS       current
    DESCRIPTION
        "The value shall be True if and only if the values of the
        transmission frequency offset parameters (provided by
        L1SyncOptParamsPortDsFrequencyOffsetTx and
        L1SyncOptParamsPortDsFrequencyOffsetTxTimestamp) are valid."
    REFERENCE    "IEEE 1588-2019: clause L.8.4.3.2"
    ::= { ieee1588L1SyncOptParamsPortDsEntry 5 }
-- .2.15.10.1.5

ieee1588L1SyncOptParamsPortDsPhaseOffsetTx OBJECT-TYPE
    SYNTAX       Ieee1588TimeInterval
    UNITS        "scaled nanoseconds"
    MAX-ACCESS   read-only
    STATUS       current
    DESCRIPTION
        "Transmission phase offset, which is the time difference between
        the significant instant with which the passage of the message
        timestamp point through the reference plane is aligned, and the
        time represented by the captured timestamp of this passage of
        the message."
    REFERENCE    "IEEE 1588-2019: clause L.8.4.3.3, L.8.2"
    ::= { ieee1588L1SyncOptParamsPortDsEntry 6 }
-- .2.15.10.1.6

ieee1588L1SyncOptParamsPortDsPhaseOffsetTxTsSecondsField OBJECT-TYPE
    SYNTAX       UInteger48
    UNITS        "seconds"
    MAX-ACCESS   read-only
    STATUS       current
    DESCRIPTION
        "Transmission phase offset timestamp for the associated
        transmission phase offset. Expressed in the timescale in use.
        Seconds part of a timestamp."
    REFERENCE    "IEEE 1588-2019: clause L.8.4.3.4, L.8.2"
    ::= { ieee1588L1SyncOptParamsPortDsEntry 7 }
-- .2.15.10.1.7

ieee1588L1SyncOptParamsPortDsPhaseOffsetTxTsNanosecondsField OBJECT-TYPE
    SYNTAX       Unsigned32(0..999999999)
    UNITS        "nanoseconds"
    MAX-ACCESS   read-only
    STATUS       current
    DESCRIPTION
        "Transmission phase offset timestamp for the associated
        transmission phase offset. Expressed in the timescale in use.
        Nanoseconds part of a timestamp."
    REFERENCE    "IEEE 1588-2019: clause L.8.4.3.4, L.8.2"
    ::= { ieee1588L1SyncOptParamsPortDsEntry 8 }
-- .2.15.10.1.8

ieee1588L1SyncOptParamsPortDsFrequencyOffsetTx OBJECT-TYPE
    SYNTAX       Ieee1588TimeInterval
    UNITS        "scaled nanoseconds"
    MAX-ACCESS   read-only
    STATUS       current
    DESCRIPTION
        "Transmission frequency offset, multiplied by one second.
        Transmission frequency offset is the known rate of change of the
        transmission phase offset."
    REFERENCE    "IEEE 1588-2019: clause L.8.4.3.5"
    ::= { ieee1588L1SyncOptParamsPortDsEntry 9 }
-- .2.15.10.1.9

ieee1588L1SyncOptParamsPortDsFrequencyOffsetTxTsSecondsField OBJECT-TYPE
    SYNTAX       UInteger48
    UNITS        "seconds"
    MAX-ACCESS   read-only
    STATUS       current
    DESCRIPTION
        "Transmission frequency offset timestamp for the associated
        transmission frequency offset. Expressed in the timescale in
        use. Seconds part of a timestamp."
    REFERENCE    "IEEE 1588-2019: clause L.8.4.3.6"
    ::= { ieee1588L1SyncOptParamsPortDsEntry 10 }
-- .2.15.10.1.10

ieee1588L1SyncOptParamsPortDsFrequencyOffsetTxTsNanosecondsField
                                                             OBJECT-TYPE
    SYNTAX       Unsigned32(0..999999999)
    UNITS        "nanoseconds"
    MAX-ACCESS   read-only
    STATUS       current
    DESCRIPTION
        "Transmission frequency offset timestamp for the associated
        transmission frequency offset. Expressed in the timescale in
        use. Nanoseconds part of a timestamp."
    REFERENCE    "IEEE 1588-2019: clause L.8.4.3.6"
    ::= { ieee1588L1SyncOptParamsPortDsEntry 11 }
-- .2.15.10.1.11

ieee1588CommunicationCapabilitiesPortDsTable OBJECT-TYPE
    SYNTAX      SEQUENCE OF Ieee1588CommunicationCapabilitiesPortDsEntry
    MAX-ACCESS   not-accessible
    STATUS       current
    DESCRIPTION
        "The communicationCapabilitiesPortDS data set for a specific PTP
        Port within PTP Instance. Provides data for multicast/unicast
        communication capabilities."
    REFERENCE    "IEEE 1588-2019: clause 8.2.25"
    ::= { ieee1588PortList 11 }
-- .2.15.11

ieee1588CommunicationCapabilitiesPortDsEntry OBJECT-TYPE
    SYNTAX       Ieee1588CommunicationCapabilitiesPortDsEntry
    MAX-ACCESS   not-accessible
    STATUS       current
    DESCRIPTION
        "An Entry providing attributes of
        communicationCapabilitiesPortDS data set for a specific PTP Port
        within PTP Instance."
    INDEX        {
        ieee1588InstanceIndex,
        ieee1588PortIndex }
    ::= { ieee1588CommunicationCapabilitiesPortDsTable 1 }
-- .2.15.11.1


Ieee1588CommunicationCapabilitiesPortDsEntry    ::= SEQUENCE {
        ieee1588CommunicationCapabilitiesPortDsSyncCapMulticastCap
                                             TruthValue,
        ieee1588CommunicationCapabilitiesPortDsSyncCapUnicastCap
                                             TruthValue,
        ieee1588CommunicationCapabilitiesPortDsSyncCapUnicastNegCap
                                             TruthValue,
        ieee1588CommunicationCapabilitiesPortDsSyncCapUnicastNegReq
                                             TruthValue,
        ieee1588CommunicationCapabilitiesPortDsDelayRespCapMulticastCap
                                             TruthValue,
        ieee1588CommunicationCapabilitiesPortDsDelayRespCapUnicastCap
                                             TruthValue,
        ieee1588CommunicationCapabilitiesPortDsDelayRespCapUnicastNegCap
                                             TruthValue,
        ieee1588CommunicationCapabilitiesPortDsDelayRespCapUnicastNegReq
                                             TruthValue
        }

ieee1588CommunicationCapabilitiesPortDsSyncCapMulticastCap OBJECT-TYPE
    SYNTAX       TruthValue
    MAX-ACCESS   read-only
    STATUS       current
    DESCRIPTION
        "This value is True if the PTP Port within PTP Instance is
        capable of transmitting PTP Sync messages using multicast
        communication."
    REFERENCE    "IEEE 1588-2019: clause 5.3.12, 8.2.25.1"
    ::= { ieee1588CommunicationCapabilitiesPortDsEntry 3 }
-- .2.15.11.1.3

ieee1588CommunicationCapabilitiesPortDsSyncCapUnicastCap OBJECT-TYPE
    SYNTAX       TruthValue
    MAX-ACCESS   read-only
    STATUS       current
    DESCRIPTION
        "This value is True if the PTP Port within PTP Instance is
        capable of transmitting PTP Sync messages using unicast
        communication."
    REFERENCE    "IEEE 1588-2019: clause 5.3.12, 8.2.25.1"
    ::= { ieee1588CommunicationCapabilitiesPortDsEntry 4 }
-- .2.15.11.1.4

ieee1588CommunicationCapabilitiesPortDsSyncCapUnicastNegCap OBJECT-TYPE
    SYNTAX       TruthValue
    MAX-ACCESS   read-only
    STATUS       current
    DESCRIPTION
        "This value is True if the PTP Port within PTP Instance is
        capable of negotiating unicast communication for PTP Sync
        messages using the unicast negotiation option and the
        ieee1588CommunicationCapabilitiesPortDsSyncCapUnicastCap is
        True."
    REFERENCE    "IEEE 1588-2019: clause 5.3.12, 8.2.25.1"
    ::= { ieee1588CommunicationCapabilitiesPortDsEntry 5 }
-- .2.15.11.1.5

ieee1588CommunicationCapabilitiesPortDsSyncCapUnicastNegReq OBJECT-TYPE
    SYNTAX       TruthValue
    MAX-ACCESS   read-only
    STATUS       current
    DESCRIPTION
        "This value is True if
        ieee1588CommunicationCapabilitiesPortDsSyncCapUnicastNegCap for
        the PTP Port within PTP Instance is True and the use of the
        unicast negotiation option for PTP Sync messages is required by
        the implementation."
    REFERENCE    "IEEE 1588-2019: clause 5.3.12, 8.2.25.1"
    ::= { ieee1588CommunicationCapabilitiesPortDsEntry 6 }
-- .2.15.11.1.6

ieee1588CommunicationCapabilitiesPortDsDelayRespCapMulticastCap
                                                             OBJECT-TYPE
    SYNTAX       TruthValue
    MAX-ACCESS   read-only
    STATUS       current
    DESCRIPTION
        "This value is True if the PTP Port within PTP Instance is
        capable of transmitting PTP Delay_Resp messages using multicast
        communication."
    REFERENCE    "IEEE 1588-2019: clause 5.3.12, 8.2.25.2"
    ::= { ieee1588CommunicationCapabilitiesPortDsEntry 7 }
-- .2.15.11.1.7

ieee1588CommunicationCapabilitiesPortDsDelayRespCapUnicastCap
                                                             OBJECT-TYPE
    SYNTAX       TruthValue
    MAX-ACCESS   read-only
    STATUS       current
    DESCRIPTION
        "This value is True if the PTP Port within PTP Instance is
        capable of transmitting PTP Delay_Resp messages using unicast
        communication."
    REFERENCE    "IEEE 1588-2019: clause 5.3.12, 8.2.25.2"
    ::= { ieee1588CommunicationCapabilitiesPortDsEntry 8 }
-- .2.15.11.1.8

ieee1588CommunicationCapabilitiesPortDsDelayRespCapUnicastNegCap
                                                             OBJECT-TYPE
    SYNTAX       TruthValue
    MAX-ACCESS   read-only
    STATUS       current
    DESCRIPTION
        "This value is True if the PTP Port within PTP Instance is
        capable of negotiating unicast communication for PTP Delay_Resp
        messages using the unicast negotiation option and the
        ieee1588CommunicationCapabilitiesPortDsDelayRespCapUnicastCap is
        True"
    REFERENCE    "IEEE 1588-2019: clause 5.3.12, 8.2.25.2"
    ::= { ieee1588CommunicationCapabilitiesPortDsEntry 9 }
-- .2.15.11.1.9

ieee1588CommunicationCapabilitiesPortDsDelayRespCapUnicastNegReq
                                                             OBJECT-TYPE
    SYNTAX       TruthValue
    MAX-ACCESS   read-only
    STATUS       current
    DESCRIPTION
        "This value is True if
        ieee1588CommunicationCapabilitiesPortDsDelayRespCapUnicastNegCap
        for the PTP Port within PTP Instance is True and the use of the
        unicast negotiation option of IEEE1588-2019 16.1 for PTP
        Delay_Resp messages is required by the implementation."
    REFERENCE    "IEEE 1588-2019: clause 5.3.12, 8.2.25.2, 16.1"
    ::= { ieee1588CommunicationCapabilitiesPortDsEntry 10 }
-- .2.15.11.1.10

ieee1588PerfMonPortDs OBJECT IDENTIFIER ::= { ieee1588PortList 12 }

ieee1588PerfMonPortDsRecordListPdTable OBJECT-TYPE
    SYNTAX       SEQUENCE OF Ieee1588PerfMonPortDsRecordListPdEntry
    MAX-ACCESS   not-accessible
    STATUS       current
    DESCRIPTION
        "Table with performance monitoring records of
        performanceMonitoringPortDS data set for a specific PTP Port
        within PTP Instance that is using the peer-to-peer (P2P) delay
        mechanism. The list is organized as follows:
        - 97 15-minute measurement records, the current record at index
        0, followed by the most recent 96 records.
        - 2 24-hour measurement records, the current record at index 97,
        and the previous record at index 98.
        If a record is not implemented for a specific index, management
        does not return the record. For example, if only four 15-minute
        periods are implemented, a management request for non-existing
        record-list returns an error.
        If only some of the data is reported, the same index values are
        used. As an example, if only the 24-hour statistics are
        accessed, the indexes are still 97 and 98.
        If a specific parameter (e.g.
        ieee1588PerfMonPortDsRecordListPdMinMeanLinkDelay) is not
        implemented, management does not return the parameter (i.e.,
        error). Parameters that are invalid (not measured correctly)
        shall be indicated with one in all bits, except the most
        significant. This represents the largest positive value of
        time-interval, indicating a value outside the maximum range."
    REFERENCE    "IEEE 1588-2019: clause 8.2.26, J.5.2"
    ::= { ieee1588PerfMonPortDs 1 }
-- .2.15.12.1

ieee1588PerfMonPortDsRecordListPdEntry OBJECT-TYPE
    SYNTAX       Ieee1588PerfMonPortDsRecordListPdEntry
    MAX-ACCESS   not-accessible
    STATUS       current
    DESCRIPTION
        "An Entry representing a performance monitoring record of a
        performanceMonitoringPortDS data set for a specific PTP Port
        within PTP Instance that is using the peer-to-peer (P2P) delay
        mechanism."
    INDEX        {
        ieee1588InstanceIndex,
        ieee1588PortIndex,
        ieee1588PerfMonPortDsRecordListPdIndex }
    ::= { ieee1588PerfMonPortDsRecordListPdTable 1 }
-- .2.15.12.1.1


Ieee1588PerfMonPortDsRecordListPdEntry    ::= SEQUENCE {
        ieee1588PerfMonPortDsRecordListPdIndex  Unsigned32,
        ieee1588PerfMonPortDsRecordListPdPmTime TimeStamp,
        ieee1588PerfMonPortDsRecordListPdAverMeanLinkDelay
                                             Ieee1588TimeInterval,
        ieee1588PerfMonPortDsRecordListPdMinMeanLinkDelay
                                             Ieee1588TimeInterval,
        ieee1588PerfMonPortDsRecordListPdMaxMeanLinkDelay
                                             Ieee1588TimeInterval,
        ieee1588PerfMonPortDsRecordListPdStdDevMLinkDelay
                                             Ieee1588TimeInterval
        }

ieee1588PerfMonPortDsRecordListPdIndex OBJECT-TYPE
    SYNTAX       Unsigned32(0..98)
    MAX-ACCESS   not-accessible
    STATUS       current
    DESCRIPTION
        "Table index of a performance monitoring record in a
        performanceMonitoringDS data set for a specific PTP Port within
        PTP Instance that is using the peer-to-peer (P2P) delay
        mechanism."
    REFERENCE    "IEEE 1588-2019: clause J.5.2.1"
    ::= { ieee1588PerfMonPortDsRecordListPdEntry 3 }
-- .2.15.12.1.1.3

ieee1588PerfMonPortDsRecordListPdPmTime OBJECT-TYPE
    SYNTAX       TimeStamp
    MAX-ACCESS   read-only
    STATUS       current
    DESCRIPTION
        "This value indicates the time of the beginning of the
        measurement period."
    REFERENCE    "IEEE 1588-2019: clause J.4.1, J.5.2.1"
    ::= { ieee1588PerfMonPortDsRecordListPdEntry 4 }
-- .2.15.12.1.1.4

ieee1588PerfMonPortDsRecordListPdAverMeanLinkDelay OBJECT-TYPE
    SYNTAX       Ieee1588TimeInterval
    UNITS        "scaled nanoseconds"
    MAX-ACCESS   read-only
    STATUS       current
    DESCRIPTION
        "Average of the meanLinkDelay for each 15 min or 24 h interval
        for a specific PTP Port within PTP Instance that is using the
        peer-to-peer (P2P) delay mechanism."
    REFERENCE    "IEEE 1588-2019: clause J.2, J.5.2.1"
    ::= { ieee1588PerfMonPortDsRecordListPdEntry 5 }
-- .2.15.12.1.1.5

ieee1588PerfMonPortDsRecordListPdMinMeanLinkDelay OBJECT-TYPE
    SYNTAX       Ieee1588TimeInterval
    UNITS        "scaled nanoseconds"
    MAX-ACCESS   read-only
    STATUS       current
    DESCRIPTION
        "Minimum of the meanLinkDelay for each 15 min or 24 h interval
        for a specific PTP Port within PTP Instance that is using the
        peer-to-peer (P2P) delay mechanism."
    REFERENCE    "IEEE 1588-2019: clause J.2, J.5.2.1"
    ::= { ieee1588PerfMonPortDsRecordListPdEntry 6 }
-- .2.15.12.1.1.6

ieee1588PerfMonPortDsRecordListPdMaxMeanLinkDelay OBJECT-TYPE
    SYNTAX       Ieee1588TimeInterval
    UNITS        "scaled nanoseconds"
    MAX-ACCESS   read-only
    STATUS       current
    DESCRIPTION
        "Maximum of the meanLinkDelay for each 15 min or 24 h interval
        for a specific PTP Port within PTP Instance that is using the
        peer-to-peer (P2P) delay mechanism."
    REFERENCE    "IEEE 1588-2019: clause J.2, J.5.2.1"
    ::= { ieee1588PerfMonPortDsRecordListPdEntry 7 }
-- .2.15.12.1.1.7

ieee1588PerfMonPortDsRecordListPdStdDevMLinkDelay OBJECT-TYPE
    SYNTAX       Ieee1588TimeInterval
    UNITS        "scaled nanoseconds"
    MAX-ACCESS   read-only
    STATUS       current
    DESCRIPTION
        "Standard deviation of the meanLinkDelay for each 15 min or 24 h
        interval for a specific PTP Port within PTP Instance that is
        using the peer-to-peer (P2P) delay mechanism."
    REFERENCE    "IEEE 1588-2019: clause J.2, J.5.2.1"
    ::= { ieee1588PerfMonPortDsRecordListPdEntry 8 }
-- .2.15.12.1.1.8

ieee1588PerfMonPortDsRecordListTable OBJECT-TYPE
    SYNTAX       SEQUENCE OF Ieee1588PerfMonPortDsRecordListEntry
    MAX-ACCESS   not-accessible
    STATUS       current
    DESCRIPTION
        "Table with performance monitoring records of
        performanceMonitoringPortDS data set not specific to the
        peer-to-peer delay measurement mechanism for a specific PTP Port
        within PTP Instance. The list is organized as follows:
        - 97 15-minute measurement records, the current record at index
        0, followed by the most recent 96 records.
        - 2 24-hour measurement records, the current record at index 97,
        and the previous record at index 98.
        If a record is not implemented for a specific index, management
        does not return the record. For example, if only four 15-minute
        periods are implemented, a management request for non-existing
        record-list returns an error.
        If only some of the data is reported, the same index values are
        used. As an example, if only the 24-hour statistics are
        accessed, the indexes are still 97 and 98.
        If a specific parameter (e.g. sync-tx) is not implemented,
        management does not return the parameter (i.e., error).
        Parameters that are invalid (not measured correctly) shall be
        indicated with with the value zero, indicating that nothing was
        counted.
        Each counter in the record shall be initialized to zero at the
        start of a new 15-minute and 24-hour interval."
    REFERENCE    "IEEE 1588-2019: clause 8.2.26, J.5.2"
    ::= { ieee1588PerfMonPortDs 2 }
-- .2.15.12.2

ieee1588PerfMonPortDsRecordListEntry OBJECT-TYPE
    SYNTAX       Ieee1588PerfMonPortDsRecordListEntry
    MAX-ACCESS   not-accessible
    STATUS       current
    DESCRIPTION
        "An Entry representing a performance monitoring record of a
        performanceMonitoringPortDS data set for a specific PTP Port
        within PTP Instance."
    INDEX        {
        ieee1588InstanceIndex,
        ieee1588PortIndex,
        ieee1588PerfMonPortDsRecordListIndex }
    ::= { ieee1588PerfMonPortDsRecordListTable 1 }
-- .2.15.12.2.1


Ieee1588PerfMonPortDsRecordListEntry    ::= SEQUENCE {
        ieee1588PerfMonPortDsRecordListIndex    Unsigned32,
        ieee1588PerfMonPortDsRecordListPmTime   TimeStamp,
        ieee1588PerfMonPortDsRecordListAnnounceTx Counter32,
        ieee1588PerfMonPortDsRecordListAnnounceRx Counter32,
        ieee1588PerfMonPortDsRecordListAnnounceFMasterRx Counter32,
        ieee1588PerfMonPortDsRecordListSyncTx   Counter32,
        ieee1588PerfMonPortDsRecordListSyncRx   Counter32,
        ieee1588PerfMonPortDsRecordListFollowUpTx Counter32,
        ieee1588PerfMonPortDsRecordListFollowUpRx Counter32,
        ieee1588PerfMonPortDsRecordListDelayReqTx Counter32,
        ieee1588PerfMonPortDsRecordListDelayReqRx Counter32,
        ieee1588PerfMonPortDsRecordListDelayRespTx Counter32,
        ieee1588PerfMonPortDsRecordListDelayRespRx Counter32,
        ieee1588PerfMonPortDsRecordListPDelayReqTx Counter32,
        ieee1588PerfMonPortDsRecordListPDelayReqRx Counter32,
        ieee1588PerfMonPortDsRecordListPDelayRespTx Counter32,
        ieee1588PerfMonPortDsRecordListPDelayRespRx Counter32,
        ieee1588PerfMonPortDsRecordListPDelayRespFollowUpTx Counter32,
        ieee1588PerfMonPortDsRecordListPDelayRespFollowUpRx Counter32
        }

ieee1588PerfMonPortDsRecordListIndex OBJECT-TYPE
    SYNTAX       Unsigned32(0..98)
    MAX-ACCESS   not-accessible
    STATUS       current
    DESCRIPTION
        "Table index of a performance monitoring record in a
        performanceMonitoringPortDS data set for a specific PTP Port
        within PTP Instance."
    REFERENCE    "IEEE 1588-2019: clause J.5.2.2"
    ::= { ieee1588PerfMonPortDsRecordListEntry 3 }
-- .2.15.12.2.1.3

ieee1588PerfMonPortDsRecordListPmTime OBJECT-TYPE
    SYNTAX       TimeStamp
    MAX-ACCESS   read-only
    STATUS       current
    DESCRIPTION
        "This value indicates the time of the beginning of the
        measurement period."
    REFERENCE    "IEEE 1588-2019: clause J.4.1, J.5.2.2"
    ::= { ieee1588PerfMonPortDsRecordListEntry 4 }
-- .2.15.12.2.1.4

ieee1588PerfMonPortDsRecordListAnnounceTx OBJECT-TYPE
    SYNTAX       Counter32
    UNITS        "messages"
    MAX-ACCESS   read-only
    STATUS       current
    DESCRIPTION
        "Counter indicating the number of Announce messages that have
        been transmitted for each 15 min or 24 h interval for a specific
        PTP Port within PTP Instance."
    REFERENCE    "IEEE 1588-2019: clause J.2, J.5.2.2"
    ::= { ieee1588PerfMonPortDsRecordListEntry 5 }
-- .2.15.12.2.1.5

ieee1588PerfMonPortDsRecordListAnnounceRx OBJECT-TYPE
    SYNTAX       Counter32
    UNITS        "messages"
    MAX-ACCESS   read-only
    STATUS       current
    DESCRIPTION
        "Counter indicating the number of Announce messages from the
        current GM that have been received for each 15 min or 24 h
        interval for a specific PTP Port within PTP Instance."
    REFERENCE    "IEEE 1588-2019: clause J.2, J.5.2.2"
    ::= { ieee1588PerfMonPortDsRecordListEntry 6 }
-- .2.15.12.2.1.6

ieee1588PerfMonPortDsRecordListAnnounceFMasterRx OBJECT-TYPE
    SYNTAX       Counter32
    UNITS        "messages"
    MAX-ACCESS   read-only
    STATUS       current
    DESCRIPTION
        "Counter indicating the total number of Announce messages from
        the foreign Masters that have been received for each 15 min or
        24 h interval for a specific PTP Port within PTP Instance."
    REFERENCE    "IEEE 1588-2019: clause J.2, J.5.2.2"
    ::= { ieee1588PerfMonPortDsRecordListEntry 7 }
-- .2.15.12.2.1.7

ieee1588PerfMonPortDsRecordListSyncTx OBJECT-TYPE
    SYNTAX       Counter32
    UNITS        "messages"
    MAX-ACCESS   read-only
    STATUS       current
    DESCRIPTION
        "Counter indicating the number of Sync messages that have been
        transmitted for each 15 min or 24 h interval for a specific PTP
        Port within PTP Instance."
    REFERENCE    "IEEE 1588-2019: clause J.2, J.5.2.2"
    ::= { ieee1588PerfMonPortDsRecordListEntry 8 }
-- .2.15.12.2.1.8

ieee1588PerfMonPortDsRecordListSyncRx OBJECT-TYPE
    SYNTAX       Counter32
    UNITS        "messages"
    MAX-ACCESS   read-only
    STATUS       current
    DESCRIPTION
        "Counter indicating the number of Sync messages that have been
        received for each 15 min or 24 h interval for a specific PTP
        Port within PTP Instance."
    REFERENCE    "IEEE 1588-2019: clause J.2, J.5.2.2"
    ::= { ieee1588PerfMonPortDsRecordListEntry 9 }
-- .2.15.12.2.1.9

ieee1588PerfMonPortDsRecordListFollowUpTx OBJECT-TYPE
    SYNTAX       Counter32
    UNITS        "messages"
    MAX-ACCESS   read-only
    STATUS       current
    DESCRIPTION
        "Counter indicating the number of Follow_Up messages that have
        been transmitted for each 15 min or 24 h interval for a specific
        PTP Port within PTP Instance."
    REFERENCE    "IEEE 1588-2019: clause J.2, J.5.2.2"
    ::= { ieee1588PerfMonPortDsRecordListEntry 10 }
-- .2.15.12.2.1.10

ieee1588PerfMonPortDsRecordListFollowUpRx OBJECT-TYPE
    SYNTAX       Counter32
    UNITS        "messages"
    MAX-ACCESS   read-only
    STATUS       current
    DESCRIPTION
        "Counter indicating the number of Follow_Up messages that have
        been received for each 15 min or 24 h interval for a specific
        PTP Port within PTP Instance."
    REFERENCE    "IEEE 1588-2019: clause J.2, J.5.2.2"
    ::= { ieee1588PerfMonPortDsRecordListEntry 11 }
-- .2.15.12.2.1.11

ieee1588PerfMonPortDsRecordListDelayReqTx OBJECT-TYPE
    SYNTAX       Counter32
    UNITS        "messages"
    MAX-ACCESS   read-only
    STATUS       current
    DESCRIPTION
        "Counter indicating the number of Delay_Req messages that have
        been transmitted for each 15 min or 24 h interval for a specific
        PTP Port within PTP Instance."
    REFERENCE    "IEEE 1588-2019: clause J.2, J.5.2.2"
    ::= { ieee1588PerfMonPortDsRecordListEntry 12 }
-- .2.15.12.2.1.12

ieee1588PerfMonPortDsRecordListDelayReqRx OBJECT-TYPE
    SYNTAX       Counter32
    UNITS        "messages"
    MAX-ACCESS   read-only
    STATUS       current
    DESCRIPTION
        "Counter indicating the number of Delay_Req messages that have
        been received for each 15 min or 24 h interval for a specific
        PTP Port within PTP Instance."
    REFERENCE    "IEEE 1588-2019: clause J.2, J.5.2.2"
    ::= { ieee1588PerfMonPortDsRecordListEntry 13 }
-- .2.15.12.2.1.13

ieee1588PerfMonPortDsRecordListDelayRespTx OBJECT-TYPE
    SYNTAX       Counter32
    UNITS        "messages"
    MAX-ACCESS   read-only
    STATUS       current
    DESCRIPTION
        "Counter indicating the number of Delay_Resp messages that have
        been transmitted for each 15 min or 24 h interval for a specific
        PTP Port within PTP Instance."
    REFERENCE    "IEEE 1588-2019: clause J.2, J.5.2.2"
    ::= { ieee1588PerfMonPortDsRecordListEntry 14 }
-- .2.15.12.2.1.14

ieee1588PerfMonPortDsRecordListDelayRespRx OBJECT-TYPE
    SYNTAX       Counter32
    UNITS        "messages"
    MAX-ACCESS   read-only
    STATUS       current
    DESCRIPTION
        "Counter indicating the number of Delay_Resp messages that have
        been received for each 15 min or 24 h interval for a specific
        PTP Port within PTP Instance."
    REFERENCE    "IEEE 1588-2019: clause J.2, J.5.2.2"
    ::= { ieee1588PerfMonPortDsRecordListEntry 15 }
-- .2.15.12.2.1.15

ieee1588PerfMonPortDsRecordListPDelayReqTx OBJECT-TYPE
    SYNTAX       Counter32
    UNITS        "messages"
    MAX-ACCESS   read-only
    STATUS       current
    DESCRIPTION
        "Counter indicating the number of Pdelay_Req messages that have
        been transmitted for each 15 min or 24 h interval for a specific
        PTP Port within PTP Instance."
    REFERENCE    "IEEE 1588-2019: clause J.2, J.5.2.2"
    ::= { ieee1588PerfMonPortDsRecordListEntry 16 }
-- .2.15.12.2.1.16

ieee1588PerfMonPortDsRecordListPDelayReqRx OBJECT-TYPE
    SYNTAX       Counter32
    UNITS        "messages"
    MAX-ACCESS   read-only
    STATUS       current
    DESCRIPTION
        "Counter indicating the number of Pdelay_Req messages that have
        been received for each 15 min or 24 h interval for a specific
        PTP Port within PTP Instance."
    REFERENCE    "IEEE 1588-2019: clause J.2, J.5.2.2"
    ::= { ieee1588PerfMonPortDsRecordListEntry 17 }
-- .2.15.12.2.1.17

ieee1588PerfMonPortDsRecordListPDelayRespTx OBJECT-TYPE
    SYNTAX       Counter32
    UNITS        "messages"
    MAX-ACCESS   read-only
    STATUS       current
    DESCRIPTION
        "Counter indicating the number of Pdelay_Resp messages that have
        been transmitted for each 15 min or 24 h interval for a specific
        PTP Port within PTP Instance."
    REFERENCE    "IEEE 1588-2019: clause J.2, J.5.2.2"
    ::= { ieee1588PerfMonPortDsRecordListEntry 18 }
-- .2.15.12.2.1.18

ieee1588PerfMonPortDsRecordListPDelayRespRx OBJECT-TYPE
    SYNTAX       Counter32
    UNITS        "messages"
    MAX-ACCESS   read-only
    STATUS       current
    DESCRIPTION
        "Counter indicating the number of Pdelay_Resp messages that have
        been received for each 15 min or 24 h interval for a specific
        PTP Port within PTP Instance."
    REFERENCE    "IEEE 1588-2019: clause J.2, J.5.2.2"
    ::= { ieee1588PerfMonPortDsRecordListEntry 19 }
-- .2.15.12.2.1.19

ieee1588PerfMonPortDsRecordListPDelayRespFollowUpTx OBJECT-TYPE
    SYNTAX       Counter32
    UNITS        "messages"
    MAX-ACCESS   read-only
    STATUS       current
    DESCRIPTION
        "Counter indicating the number of Pdelay_Resp_Follow_Up messages
        that have been transmitted for each 15 min or 24 h interval for
        a specific PTP Port within PTP Instance."
    REFERENCE    "IEEE 1588-2019: clause J.2, J.5.2.2"
    ::= { ieee1588PerfMonPortDsRecordListEntry 20 }
-- .2.15.12.2.1.20

ieee1588PerfMonPortDsRecordListPDelayRespFollowUpRx OBJECT-TYPE
    SYNTAX       Counter32
    UNITS        "messages"
    MAX-ACCESS   read-only
    STATUS       current
    DESCRIPTION
        "Counter indicating the number of Pdelay_Resp_Follow_Up messages
        that have been received for each 15 min or 24 h interval for a
        specific PTP Port within PTP Instance."
    REFERENCE    "IEEE 1588-2019: clause J.2, J.5.2.2"
    ::= { ieee1588PerfMonPortDsRecordListEntry 21 }
-- .2.15.12.2.1.21

ieee1588SlaveMonitoringPortDsTable OBJECT-TYPE
    SYNTAX       SEQUENCE OF Ieee1588SlaveMonitoringPortDsEntry
    MAX-ACCESS   not-accessible
    STATUS       current
    DESCRIPTION
        "The slaveMonitoringPortDS data set for a specific PTP Port
        within PTP Instance. Provides management access to the optional
        Slave Event Monitor service."
    REFERENCE    "IEEE 1588-2019: clause 8.2.29, 16.11.6"
    ::= { ieee1588PortList 13 }
-- .2.15.13

ieee1588SlaveMonitoringPortDsEntry OBJECT-TYPE
    SYNTAX       Ieee1588SlaveMonitoringPortDsEntry
    MAX-ACCESS   not-accessible
    STATUS       current
    DESCRIPTION
        "An Entry providing attributes of slaveMonitoringPortDS data set
        for a specific PTP Port within PTP Instance."
    INDEX        {
        ieee1588InstanceIndex,
        ieee1588PortIndex }
    ::= { ieee1588SlaveMonitoringPortDsTable 1 }
-- .2.15.13.1


Ieee1588SlaveMonitoringPortDsEntry    ::= SEQUENCE {
        ieee1588SlaveMonitoringPortDsSlaveEventMonEnable BITS,
        ieee1588SlaveMonitoringPortDsSlaveEventMonEventsPerRxSyncTimTLV
                                             Unsigned32,
        ieee1588SlaveMonitoringPortDsSlaveEventMonEventsPerRxSyncCompTLV
                                             Unsigned32,
        ieee1588SlaveMonitoringPortDsSlaveEventMonEventsPerTxEventTsTLV
                                             Unsigned32,
        ieee1588SlaveMonitoringPortDsSlaveEventMonTxEventType
                                             Ieee1588MessageType,
        ieee1588SlaveMonitoringPortDsSlaveEventMonRxSyncTimEventMsgM
                                             Unsigned32,
        ieee1588SlaveMonitoringPortDsSlaveEventMonRxSyncCompEventMsgM
                                             Unsigned32,
        ieee1588SlaveMonitoringPortDsSlaveEventMonTxEventTsEventMsgM
                                             Unsigned32
        }

ieee1588SlaveMonitoringPortDsSlaveEventMonEnable OBJECT-TYPE
    SYNTAX       BITS {
        ieee1588SlaveMonitoringPortDsSlaveEventMonEnableSlaveRxSyncTim(0),
        ieee1588SlaveMonitoringPortDsSlaveEventMonEnableSlaveRxSyncComp(1),
        ieee1588SlaveMonitoringPortDsSlaveEventMonEnableSlaveTxEventTsD(2)
        }
    MAX-ACCESS   read-write
    STATUS       current
    DESCRIPTION
        "This bitfield value indicates whether the data for the slave
        event monitoring TLVs are computed, and whether the data are
        transmitted by the slave.
        ieee1588SlaveMonitoringPortDsSlaveEventMonEnableSlaveRxSyncTim -
        True activates generation of the SLAVE_RX_SYNC_TIMING_DATA TLV.
        ieee1588SlaveMonitoringPortDsSlaveEventMonEnableSlaveRxSyncComp
        - True activates generation of the SLAVE_RX_SYNC_COMPUTED_DATA
        TLV.
        ieee1588SlaveMonitoringPortDsSlaveEventMonEnableSlaveTxEventTsD
        - True activates generation of the
        SLAVE_TX_EVENT_TIMESTAMPS_DATA TLV."
    REFERENCE    "IEEE 1588-2019: clause 16.11.6.2"
    ::= { ieee1588SlaveMonitoringPortDsEntry 3 }
-- .2.15.13.1.3

ieee1588SlaveMonitoringPortDsSlaveEventMonEventsPerRxSyncTimTLV
                                                             OBJECT-TYPE
    SYNTAX       Unsigned32(0..255)
    UNITS        "events"
    MAX-ACCESS   read-write
    STATUS       current
    DESCRIPTION
        "This value indicates the number of events to report per
        SLAVE_RX_SYNC_TIMING_DATA TLV."
    REFERENCE    "IEEE 1588-2019: clause 16.11.6.3"
    ::= { ieee1588SlaveMonitoringPortDsEntry 4 }
-- .2.15.13.1.4

ieee1588SlaveMonitoringPortDsSlaveEventMonEventsPerRxSyncCompTLV
                                                             OBJECT-TYPE
    SYNTAX       Unsigned32(0..255)
    UNITS        "events"
    MAX-ACCESS   read-write
    STATUS       current
    DESCRIPTION
        "This value indicates the number of events to report per
        SLAVE_RX_SYNC_COMPUTED_DATA TLV."
    REFERENCE    "IEEE 1588-2019: clause 16.11.6.4"
    ::= { ieee1588SlaveMonitoringPortDsEntry 5 }
-- .2.15.13.1.5

ieee1588SlaveMonitoringPortDsSlaveEventMonEventsPerTxEventTsTLV
                                                             OBJECT-TYPE
    SYNTAX       Unsigned32(0..255)
    UNITS        "events"
    MAX-ACCESS   read-write
    STATUS       current
    DESCRIPTION
        "This value indicates the number of events to report per
        SLAVE_TX_EVENT_TIMESTAMPS_DATA TLV."
    REFERENCE    "IEEE 1588-2019: clause 16.11.6.5"
    ::= { ieee1588SlaveMonitoringPortDsEntry 6 }
-- .2.15.13.1.6

ieee1588SlaveMonitoringPortDsSlaveEventMonTxEventType OBJECT-TYPE
    SYNTAX       Ieee1588MessageType
    MAX-ACCESS   read-write
    STATUS       current
    DESCRIPTION
        "This value indicates the event message type selected for the
        egress event monitoring."
    REFERENCE    "IEEE 1588-2019: clause 16.11.6.6"
    ::= { ieee1588SlaveMonitoringPortDsEntry 7 }
-- .2.15.13.1.7

ieee1588SlaveMonitoringPortDsSlaveEventMonRxSyncTimEventMsgM OBJECT-TYPE
    SYNTAX       Unsigned32(0..255)
    UNITS        "events"
    MAX-ACCESS   read-write
    STATUS       current
    DESCRIPTION
        "The value M, where M indicates that every Mth event message is
        selected for monitoring in the SLAVE_RX_SYNC_TIMING_DATA TLV.
        For example, if the value of M is 4, every fourth event message
        is selected for monitoring in the TLV."
    REFERENCE    "IEEE 1588-2019: clause 16.11.6.7"
    ::= { ieee1588SlaveMonitoringPortDsEntry 8 }
-- .2.15.13.1.8

ieee1588SlaveMonitoringPortDsSlaveEventMonRxSyncCompEventMsgM
                                                             OBJECT-TYPE
    SYNTAX       Unsigned32(0..255)
    UNITS        "events"
    MAX-ACCESS   read-write
    STATUS       current
    DESCRIPTION
        "The value M, where M indicates that every Mth event message is
        selected for monitoring in the SLAVE_RX_SYNC_COMPUTED_DATA TLV.
        For example, if the value of M is 4, every fourth event message
        is selected for monitoring in the TLV."
    REFERENCE    "IEEE 1588-2019: clause 16.11.6.8"
    ::= { ieee1588SlaveMonitoringPortDsEntry 9 }
-- .2.15.13.1.9

ieee1588SlaveMonitoringPortDsSlaveEventMonTxEventTsEventMsgM OBJECT-TYPE
    SYNTAX       Unsigned32(0..255)
    UNITS        "events"
    MAX-ACCESS   read-write
    STATUS       current
    DESCRIPTION
        "The value M, where M indicates that every Mth event message is
        selected for monitoring in the SLAVE_TX_EVENT_TIMESTAMPS_DATA
        TLV. For example, if the value of M is 4, every fourth event
        message is selected for monitoring in the TLV."
    REFERENCE    "IEEE 1588-2019: clause 16.11.6.9"
    ::= { ieee1588SlaveMonitoringPortDsEntry 10 }
-- .2.15.13.1.10

ieee1588CommonServicesPortDsTable OBJECT-TYPE
    SYNTAX       SEQUENCE OF Ieee1588CommonServicesPortDsEntry
    MAX-ACCESS   not-accessible
    STATUS       current
    DESCRIPTION
        "The commonServicesPortDS data set for a specific PTP Port
        within PTP Instance. Provides management access to the common
        services, scoped to each PTP Port for a specific PTP Port within
        PTP Instance."
    REFERENCE    "IEEE 1588-2019: clause 16.6.5, 8.2.27"
    ::= { ieee1588PortList 14 }
-- .2.15.14

ieee1588CommonServicesPortDsEntry OBJECT-TYPE
    SYNTAX       Ieee1588CommonServicesPortDsEntry
    MAX-ACCESS   not-accessible
    STATUS       current
    DESCRIPTION
        "An Entry providing attributes of commonServicesPortDS data set
        for a specific PTP Port within PTP Instance."
    INDEX        {
        ieee1588InstanceIndex,
        ieee1588PortIndex }
    ::= { ieee1588CommonServicesPortDsTable 1 }
-- .2.15.14.1


Ieee1588CommonServicesPortDsEntry    ::= SEQUENCE {
        ieee1588CommonServicesPortDsCmldsLinkPortPortNumber Unsigned32
        }

ieee1588CommonServicesPortDsCmldsLinkPortPortNumber OBJECT-TYPE
    SYNTAX       Unsigned32(0..65535)
    MAX-ACCESS   read-only
    STATUS       current
    DESCRIPTION
        "Common services operate on all PTP Instances of the PTP Node.
        When a common service has port-specific behavior, it specifies a
        Link Port, which represents the physical port that the service
        uses to transport PTP messages. In the context of such a common
        service, the PTP Port represents a logical port.
        The Common Mean Link Delay Service (CMLDS) is port-specific, and
        this object provides the mapping of the PTP Port of this PTP
        Instance to the corresponding Link Port in CMLDS. The Link Port
        is identified using an IEEE Std 1588 portNumber. The
        corresponding Link Port's portNumber is located in the hierarchy
        at ieee1588CmldsLinkPortDsPortIdentityPortNumber."
    REFERENCE    "IEEE 1588-2019: clause 16.6.5.1.1.1"
    ::= { ieee1588CommonServicesPortDsEntry 3 }
-- .2.15.14.1.3

ieee1588ExternalPortConfigurationPortDsTable OBJECT-TYPE
    SYNTAX      SEQUENCE OF Ieee1588ExternalPortConfigurationPortDsEntry
    MAX-ACCESS   not-accessible
    STATUS       current
    DESCRIPTION
        "The externalPortConfigurationPortDS data set for a specific PTP
        Port within PTP Instance. Provides management access to the
        external configuration option."
    REFERENCE    "IEEE 1588-2019: clause 17.6.3, 8.2.28"
    ::= { ieee1588PortList 15 }
-- .2.15.15

ieee1588ExternalPortConfigurationPortDsEntry OBJECT-TYPE
    SYNTAX       Ieee1588ExternalPortConfigurationPortDsEntry
    MAX-ACCESS   not-accessible
    STATUS       current
    DESCRIPTION
        "An Entry providing attributes of
        externalPortConfigurationPortDS data set for a specific PTP Port
        within PTP Instance."
    INDEX        {
        ieee1588InstanceIndex,
        ieee1588PortIndex }
    ::= { ieee1588ExternalPortConfigurationPortDsTable 1 }
-- .2.15.15.1


Ieee1588ExternalPortConfigurationPortDsEntry    ::= SEQUENCE {
        ieee1588ExternalPortConfigurationPortDsDesiredState
                                             Ieee1588PortState
        }

ieee1588ExternalPortConfigurationPortDsDesiredState OBJECT-TYPE
    SYNTAX       Ieee1588PortState
    MAX-ACCESS   read-write
    STATUS       current
    DESCRIPTION
        "When the value of
        ieee1588DefaultDsExternalPortConfigurationEnabled is true, this
        desired-state is used to externally configure the PTP Port's
        state to a desired value."
    REFERENCE    "IEEE 1588-2019: clause 17.6.3.2"
    ::= { ieee1588ExternalPortConfigurationPortDsEntry 3 }
-- .2.15.15.1.3

ieee1588TcDefaultDs OBJECT IDENTIFIER ::= { ieee1588Objects 3 }

ieee1588TcDefaultDsClockIdentity OBJECT-TYPE
    SYNTAX       Ieee1588ClockIdentity
    MAX-ACCESS   read-only
    STATUS       deprecated
    DESCRIPTION
        "The clockIdentity of the local clock.
        This default data set was specified in IEEE Std 1588-2008, and
        under some interpretations, it applied to all domains, which in
        turn means that it represents multiple Transparent Clocks.
        In IEEE Std 1588-2019, this data set is specified as applying to
        the PTP Node (all domains), but the data set is deprecated. For
        new designs, the standard recommends that Transparent Clocks use
        the PTP Instance data sets (under ieee1588Instances), such that
        each Transparent Clock supports a single PTP Instance and
        domain."
    REFERENCE    "IEEE 1588-2019: clause 8.3.2.2.1"
    ::= { ieee1588TcDefaultDs 1 }
-- .3.1

ieee1588TcDefaultDsNumberPorts OBJECT-TYPE
    SYNTAX       Unsigned32(0..65535)
    MAX-ACCESS   read-only
    STATUS       deprecated
    DESCRIPTION
        "The number of PTP Ports of the device.
        This default data set was specified in IEEE Std 1588-2008, and
        under some interpretations, it applied to all domains, which in
        turn means that it represents multiple Transparent Clocks.
        In IEEE Std 1588-2019, this data set is specified as applying to
        the PTP Node (all domains), but the data set is deprecated. For
        new designs, the standard recommends that Transparent Clocks use
        the PTP Instance data sets (under ieee1588Instances), such that
        each Transparent Clock supports a single PTP Instance and
        domain."
    REFERENCE    "IEEE 1588-2019: clause 8.3.2.2.2"
    ::= { ieee1588TcDefaultDs 2 }
-- .3.2

ieee1588TcDefaultDsDelayMechanism OBJECT-TYPE
    SYNTAX       Ieee1588DelayMechanism
    MAX-ACCESS   read-write
    STATUS       deprecated
    DESCRIPTION
        "The propagation delay measuring mechanism (e2e or p2p) used by
        a Transparent Clock.
        This default data set was specified in IEEE Std 1588-2008, and
        under some interpretations, it applied to all domains, which in
        turn means that it represents multiple Transparent Clocks.
        In IEEE Std 1588-2019, this data set is specified as applying to
        the PTP Node (all domains), but the data set is deprecated. For
        new designs, the standard recommends that Transparent Clocks use
        the PTP Instance data sets (under ieee1588Instances), such that
        each Transparent Clock supports a single PTP Instance and
        domain."
    REFERENCE    "IEEE 1588-2019: clause 8.3.2.3.1"
    ::= { ieee1588TcDefaultDs 3 }
-- .3.3

ieee1588TcDefaultDsPrimaryDomain OBJECT-TYPE
    SYNTAX       Unsigned32(0..255)
    MAX-ACCESS   read-write
    STATUS       deprecated
    DESCRIPTION
        "The domainNumber of the primary syntonization domain used by a
        Transparent Clock.
        This default data set was specified in IEEE Std 1588-2008, and
        under some interpretations, it applied to all domains, which in
        turn means that it represents multiple Transparent Clocks.
        In IEEE Std 1588-2019, this data set is specified as applying to
        the PTP Node (all domains), but the data set is deprecated. For
        new designs, the standard recommends that Transparent Clocks use
        the PTP Instance data sets (under ieee1588Instances), such that
        each Transparent Clock supports a single PTP Instance and
        domain."
    REFERENCE    "IEEE 1588-2019: clause 8.3.2.3.2"
    ::= { ieee1588TcDefaultDs 4 }
-- .3.4

ieee1588TcPortList OBJECT IDENTIFIER ::= { ieee1588Objects 4 }

ieee1588TcPortDsTable OBJECT-TYPE
    SYNTAX       SEQUENCE OF Ieee1588TcPortDsEntry
    MAX-ACCESS   not-accessible
    STATUS       deprecated
    DESCRIPTION
        "Table with records of transparentClockPortDS data set for a
        specific PTP Port. IEEE 1588-2019 standard specifies
        transparentClockPortDS as applying to the PTP Node, but it
        designates this data set as deprecated. This data set operate on
        all domains, and therefore, it represent multiple PTP Instances
        (i.e., multiple Transparent Clocks)."
    REFERENCE    "IEEE 1588-2019: clause 8.3.3, 8.3.1.1"
    ::= { ieee1588TcPortList 1 }
-- .4.1

ieee1588TcPortDsEntry OBJECT-TYPE
    SYNTAX       Ieee1588TcPortDsEntry
    MAX-ACCESS   not-accessible
    STATUS       deprecated
    DESCRIPTION
        "An Entry providing attributes of transparentClockPortDS data
        set for a specific PTP Port. IEEE 1588-2019 standard specifies
        transparentClockPortDS as applying to the PTP Node, but it
        designates this data set as deprecated. This data set operate on
        all domains, and therefore, it represent multiple PTP Instances
        (i.e., multiple Transparent Clocks)."
    INDEX        {
        ieee1588TcLocalPortIndex }
    ::= { ieee1588TcPortDsTable 1 }
-- .4.1.1


Ieee1588TcPortDsEntry    ::= SEQUENCE {
        ieee1588TcLocalPortIndex                Unsigned32,
        ieee1588TcPortDsLocalPortIfIndex        InterfaceIndexOrZero,
        ieee1588TcPortDsPortIdentityClockIdentity Ieee1588ClockIdentity,
        ieee1588TcPortDsPortIdentityPortNumber  Unsigned32,
        ieee1588TcPortDsLogMinPdelayReqInterv   Ieee1588LogTimeInterval,
        ieee1588TcPortDsFaultyFlag              TruthValue,
        ieee1588TcPortDsPeerMeanPathDelay       Ieee1588TimeInterval
        }

ieee1588TcLocalPortIndex OBJECT-TYPE
    SYNTAX       Unsigned32(1..65534)
    MAX-ACCESS   not-accessible
    STATUS       deprecated
    DESCRIPTION
        "An index that is unique per Local Port within the PTP Node (see
        NOTE in 8.3.3.2.1), applicable to the management context only
        (i.e. not used in PTP messages).
        NOTE: this number might not be equivalent to the portNumber
        attribute (transparentClockPortDS.portIdentity.portNumber data
        set member)."
    REFERENCE    "IEEE 1588-2019: clause 8.3.3.2.1"
    ::= { ieee1588TcPortDsEntry 1 }
-- .4.1.1.1

ieee1588TcPortDsLocalPortIfIndex OBJECT-TYPE
    SYNTAX       InterfaceIndexOrZero
    MAX-ACCESS   read-only
    STATUS       deprecated
    DESCRIPTION
        "This value can be used to identify the interface used by the
        respective Local Port (see NOTE in 8.3.3.2.1).
        If this value is non-zero, it refers to the ifIndex object of
        the used interface in the ifTable (IF-MIB)."
    REFERENCE    "IEEE 1588-2019: clause 8.3.3.2.1"
    ::= { ieee1588TcPortDsEntry 2 }
-- .4.1.1.2

ieee1588TcPortDsPortIdentityClockIdentity OBJECT-TYPE
    SYNTAX       Ieee1588ClockIdentity
    MAX-ACCESS   read-only
    STATUS       deprecated
    DESCRIPTION
        "The portIdentity.clockIdentity attribute of the local port.
        This data set member was specified in IEEE Std 1588-2008, and
        under some interpretations, it applied to all domains, which in
        turn means that it represents multiple Transparent Clocks. In
        IEEE Std 1588-2019, this data set is specified as applying to
        the PTP Node (all domains), but the data set is deprecated. For
        new designs, the standard recommends that Transparent Clocks use
        the PTP Instance data sets (under ieee1588Instances), such that
        each Transparent Clock supports a single PTP Instance and
        domain."
    REFERENCE    "IEEE 1588-2019: clause 8.3.3.2.1"
    ::= { ieee1588TcPortDsEntry 3 }
-- .4.1.1.3

ieee1588TcPortDsPortIdentityPortNumber OBJECT-TYPE
    SYNTAX       Unsigned32(0..65535)
    MAX-ACCESS   read-only
    STATUS       deprecated
    DESCRIPTION
        "The portIdentity.portNumber attribute of the local port
        This data set member was specified in IEEE Std 1588-2008, and
        under some interpretations, it applied to all domains, which in
        turn means that it represents multiple Transparent Clocks. In
        IEEE Std 1588-2019, this data set is specified as applying to
        the PTP Node (all domains), but the data set is deprecated. For
        new designs, the standard recommends that Transparent Clocks use
        the PTP Instance data sets (under ieee1588Instances), such that
        each Transparent Clock supports a single PTP Instance and
        domain."
    REFERENCE    "IEEE 1588-2019: clause 8.3.3.2.1"
    ::= { ieee1588TcPortDsEntry 4 }
-- .4.1.1.4

ieee1588TcPortDsLogMinPdelayReqInterv OBJECT-TYPE
    SYNTAX       Ieee1588LogTimeInterval
    UNITS        "log2 seconds"
    MAX-ACCESS   read-only
    STATUS       deprecated
    DESCRIPTION
        "The logarithm to the base 2 of the minPdelayReqInterval
        (minimum permitted mean time interval between successive
        Pdelay_Req messages).
        This data set member was specified in IEEE Std 1588-2008, and
        under some interpretations, it applied to all domains, which in
        turn means that it represents multiple Transparent Clocks. In
        IEEE Std 1588-2019, this data set is specified as applying to
        the PTP Node (all domains), but the data set is deprecated. For
        new designs, the standard recommends that Transparent Clocks use
        the PTP Instance data sets (under ieee1588Instances), such that
        each Transparent Clock supports a single PTP Instance and
        domain."
    REFERENCE    "IEEE 1588-2019: clause 8.3.3.3.1"
    ::= { ieee1588TcPortDsEntry 5 }
-- .4.1.1.5

ieee1588TcPortDsFaultyFlag OBJECT-TYPE
    SYNTAX       TruthValue
    MAX-ACCESS   read-only
    STATUS       deprecated
    DESCRIPTION
        "Shall be true if the port is faulty and false if the port is
        operating normally.
        This data set member was specified in IEEE Std 1588-2008, and
        under some interpretations, it applied to all domains, which in
        turn means that it represents multiple Transparent Clocks. In
        IEEE Std 1588-2019, this data set is specified as applying to
        the PTP Node (all domains), but the data set is deprecated. For
        new designs, the standard recommends that Transparent Clocks use
        the PTP Instance data sets (under ieee1588Instances), such that
        each Transparent Clock supports a single PTP Instance and
        domain."
    REFERENCE    "IEEE 1588-2019: clause 8.3.3.3.2"
    ::= { ieee1588TcPortDsEntry 6 }
-- .4.1.1.6

ieee1588TcPortDsPeerMeanPathDelay OBJECT-TYPE
    SYNTAX       Ieee1588TimeInterval
    UNITS        "scaled nanoseconds"
    MAX-ACCESS   read-only
    STATUS       deprecated
    DESCRIPTION
        "An estimate of the current one-way propagation delay on the
        link when the delayMechanism is P2P; otherwise, it is zero.
        This data set member was specified in IEEE Std 1588-2008, and
        under some interpretations, it applied to all domains, which in
        turn means that it represents multiple Transparent Clocks. In
        IEEE Std 1588-2019, this data set is specified as applying to
        the PTP Node (all domains), but the data set is deprecated. For
        new designs, the standard recommends that Transparent Clocks use
        the PTP Instance data sets (under ieee1588Instances), such that
        each Transparent Clock supports a single PTP Instance and
        domain."
    REFERENCE    "IEEE 1588-2019: clause 8.3.3.3.3"
    ::= { ieee1588TcPortDsEntry 7 }
-- .4.1.1.7

ieee1588CommonServices OBJECT IDENTIFIER ::= { ieee1588Objects 5 }

ieee1588CommonMeanLinkDelayService
                      OBJECT IDENTIFIER ::= { ieee1588CommonServices 1 }

ieee1588CmldsDefaultDs
          OBJECT IDENTIFIER ::= { ieee1588CommonMeanLinkDelayService 1 }

ieee1588CmldsDefaultDsClockIdentity OBJECT-TYPE
    SYNTAX       Ieee1588ClockIdentity
    MAX-ACCESS   read-only
    STATUS       deprecated
    DESCRIPTION
        "The IEEE Std 1588 clockIdentity used by The Common Mean Link
        Delay Service (CMLDS). CMLDS is an optional service that enables
        any Link Port that would normally obtain the value of a link's
        <meanLinkDelay> and <neighborRateRatio> using the peer-to-peer
        method to instead obtain these values from this optional
        service.
        The CMLDS service is available to all PTP Nodes communicating
        with a specific transport mechanism."
    REFERENCE    "IEEE 1588-2019: clause 16.6.4.1.2.1"
    ::= { ieee1588CmldsDefaultDs 1 }
-- .5.1.1.1

ieee1588CmldsDefaultDsNumberLinkPorts OBJECT-TYPE
    SYNTAX       Unsigned32(0..65535)
    MAX-ACCESS   read-only
    STATUS       deprecated
    DESCRIPTION
        "The number of Link Ports of The Common Mean Link Delay Service
        (CMLDS). CMLDS is an optional service that enables any Link Port
        that would normally obtain the value of a link's <meanLinkDelay>
        and <neighborRateRatio> using the peer-to-peer method to instead
        obtain these values from this optional service.
        The CMLDS service is available to all PTP Nodes communicating
        with a specific transport mechanism.
        "
    REFERENCE    "IEEE 1588-2019: clause 16.6.4.1.2.2"
    ::= { ieee1588CmldsDefaultDs 2 }
-- .5.1.1.2

ieee1588CmldsLinkPortList
          OBJECT IDENTIFIER ::= { ieee1588CommonMeanLinkDelayService 2 }

ieee1588CmldsLinkPortDsTable OBJECT-TYPE
    SYNTAX       SEQUENCE OF Ieee1588CmldsLinkPortDsEntry
    MAX-ACCESS   not-accessible
    STATUS       current
    DESCRIPTION
        "The cmldsLinkPortDS data set with data for Common Mean Link
        Delay Service (CMLDS) for each Link Port.
        The Common Mean Link Delay Service (CMLDS) is an optional
        service that enables any Link Port that would normally obtain
        the value of a link's <meanLinkDelay> and <neighborRateRatio>
        using the peer-to-peer method to instead obtain these values
        from this optional service. The CMLDS service is available to
        all PTP Nodes communicating with a specific transport mechanism.
        The Common Mean Link Delay Service is designed to run
        independently from any PTP Nodes communicating over a Link Port.
        The service provides information on the <meanLinkDelay> as well
        as the <neighborRateRatio> measured in the timescale used by the
        service. The service runs on every Link Port where the CMLDS is
        present. Information required by a Link Port is requested from
        and delivered by the service running on the associated Link
        Port."
    REFERENCE    "IEEE 1588-2019: clause 16.6.4.2"
    ::= { ieee1588CmldsLinkPortList 1 }
-- .5.1.2.1

ieee1588CmldsLinkPortDsEntry OBJECT-TYPE
    SYNTAX       Ieee1588CmldsLinkPortDsEntry
    MAX-ACCESS   not-accessible
    STATUS       current
    DESCRIPTION
        "An Entry providing attributes of cmldsLinkPortDS data set with
        data for Common Mean Link Delay Service for a specific Link
        Port."
    INDEX        {
        ieee1588LinkPortIndex }
    ::= { ieee1588CmldsLinkPortDsTable 1 }
-- .5.1.2.1.1


Ieee1588CmldsLinkPortDsEntry    ::= SEQUENCE {
        ieee1588LinkPortIndex                   Unsigned32,
        ieee1588CmldsLinkPortDsPortIdentityClockIdentity
                                             Ieee1588ClockIdentity,
        ieee1588CmldsLinkPortDsPortIdentityPortNumber Unsigned32,
        ieee1588CmldsLinkPortDsCmldiServiceMeasurementValid TruthValue,
        ieee1588CmldsLinkPortDsCmldiMeanLinkDelay Ieee1588TimeInterval,
        ieee1588CmldsLinkPortDsCmldiScaledNeighborRateRatio Integer32,
        ieee1588CmldsLinkPortDsLogMinPdelayReqInterval
                                             Ieee1588LogTimeInterval,
        ieee1588CmldsLinkPortDsVersionNumber    Unsigned32,
        ieee1588CmldsLinkPortDsMinorVersionNumber Unsigned32,
        ieee1588CmldsLinkPortDsDelayAsymmetry   Ieee1588TimeInterval,
        ieee1588CmldsLinkPortDsDomainNumber     Unsigned32
        }

ieee1588LinkPortIndex OBJECT-TYPE
    SYNTAX       Unsigned32(1..65534)
    MAX-ACCESS   not-accessible
    STATUS       current
    DESCRIPTION
        "An index that is unique per Link Port, applicable to the
        management context only (i.e. not used in PTP messages). The
        Link Port value shall be unique to the Link Port."
    ::= { ieee1588CmldsLinkPortDsEntry 1 }
-- .5.1.2.1.1.1

ieee1588CmldsLinkPortDsPortIdentityClockIdentity OBJECT-TYPE
    SYNTAX       Ieee1588ClockIdentity
    MAX-ACCESS   read-only
    STATUS       current
    DESCRIPTION
        "The clockIdentity of this Link Port. This leaf is equal to the
        clock-identity leaf ieee1588CmldsDefaultDsClockIdentity in
        defaultDs of the CMLDS."
    REFERENCE    "IEEE 1588-2019: clause 16.6.4.2.2.1"
    ::= { ieee1588CmldsLinkPortDsEntry 2 }
-- .5.1.2.1.1.2

ieee1588CmldsLinkPortDsPortIdentityPortNumber OBJECT-TYPE
    SYNTAX       Unsigned32
    MAX-ACCESS   read-only
    STATUS       current
    DESCRIPTION
        "The portNumber of this Link Port. If portNumber is unavailable,
        the value 0 can be used, or this object can be omitted.
        CMLDS specifies a Link Port, which represents the physical port
        that the service uses to transport PTP messages. This object
        provides the mapping of the Link Port in CMLDS to the
        corresponding Link Ports in PTP Nodes. The Link Port is
        identified using an IEEE Std 1588 portNumber."
    REFERENCE    "IEEE 1588-2019: clause 16.6.4.2.2.1"
    ::= { ieee1588CmldsLinkPortDsEntry 3 }
-- .5.1.2.1.1.3

ieee1588CmldsLinkPortDsCmldiServiceMeasurementValid OBJECT-TYPE
    SYNTAX       TruthValue
    MAX-ACCESS   read-only
    STATUS       current
    DESCRIPTION
        "This object is initialized to false, and will be false whenever
        the required PTP messages for CMLDS are not received on the Link
        Port. When the required PTP messages for CMLDS are received,
        this object is true."
    REFERENCE    "IEEE 1588-2019: clause 16.6.4.2.3.1, 16.6.3.2"
    ::= { ieee1588CmldsLinkPortDsEntry 4 }
-- .5.1.2.1.1.4

ieee1588CmldsLinkPortDsCmldiMeanLinkDelay OBJECT-TYPE
    SYNTAX       Ieee1588TimeInterval
    UNITS        "scaled nanoseconds"
    MAX-ACCESS   read-only
    STATUS       current
    DESCRIPTION
        "Estimate of the current one-way propagation delay on the PTP
        Link, i.e., <meanLinkDelay>, attached to this Link Port,
        computed using the peer-to-peer delay mechanism."
    REFERENCE    "IEEE 1588-2019: clause 16.6.4.2.3.1, 16.6.3.2"
    ::= { ieee1588CmldsLinkPortDsEntry 5 }
-- .5.1.2.1.1.5

ieee1588CmldsLinkPortDsCmldiScaledNeighborRateRatio OBJECT-TYPE
    SYNTAX       Integer32
    MAX-ACCESS   read-only
    STATUS       current
    DESCRIPTION
        "Ratio of the rate of this PTP Node's clock to the clock of its
        neighbor attached to this Link Port, i.e., <neighborRateRatio>,
        scaled as specified in the standard."
    REFERENCE    "IEEE 1588-2019: clause 16.6.4.2.3.1, 16.6.3.2"
    ::= { ieee1588CmldsLinkPortDsEntry 6 }
-- .5.1.2.1.1.6

ieee1588CmldsLinkPortDsLogMinPdelayReqInterval OBJECT-TYPE
    SYNTAX       Ieee1588LogTimeInterval
    UNITS        "log2 seconds"
    MAX-ACCESS   read-write
    STATUS       current
    DESCRIPTION
        "Logarithm to the base 2 of the IEEE Std 1588
        minPdelayReqInterval, the minimum permitted mean time interval
        between successive Pdelay_Req messages sent by CMLDS."
    REFERENCE    "IEEE 1588-2019: clause 16.6.4.2.4.1"
    ::= { ieee1588CmldsLinkPortDsEntry 7 }
-- .5.1.2.1.1.7

ieee1588CmldsLinkPortDsVersionNumber OBJECT-TYPE
    SYNTAX       Unsigned32(0..15)
    MAX-ACCESS   read-write
    STATUS       current
    DESCRIPTION
        "The PTP major version in use on the Link Port.
        NOTE - This indicates the version of the IEEE 1588 standard, and
        not the version of an applicable PTP Profile. It is 2 for IEEE
        Std 1588-2008 and IEEE Std 1588-2019."
    REFERENCE    "IEEE 1588-2019: clause 16.6.4.2.4.2"
    ::= { ieee1588CmldsLinkPortDsEntry 8 }
-- .5.1.2.1.1.8

ieee1588CmldsLinkPortDsMinorVersionNumber OBJECT-TYPE
    SYNTAX       Unsigned32(0..15)
    MAX-ACCESS   read-write
    STATUS       current
    DESCRIPTION
        "The PTP minor version in use on the Link Port.
        NOTE - This indicates the version of the IEEE 1588 standard, and
        not the version of an applicable PTP Profile. It is 0 for IEEE
        Std 1588-2008 and 1 for IEEE Std 1588-2019."
    REFERENCE    "IEEE 1588-2019: clause 16.6.4.2.4.3"
    ::= { ieee1588CmldsLinkPortDsEntry 9 }
-- .5.1.2.1.1.9

ieee1588CmldsLinkPortDsDelayAsymmetry OBJECT-TYPE
    SYNTAX       Ieee1588TimeInterval
    UNITS        "scaled nanoseconds"
    MAX-ACCESS   read-write
    STATUS       current
    DESCRIPTION
        "The value of delayAsymmetry applicable to the Link Port, which
        is the difference in transmission time in one direction as
        compared to the opposite direction."
    REFERENCE    "IEEE 1588-2019: clause 16.6.4.2.4.4"
    ::= { ieee1588CmldsLinkPortDsEntry 10 }
-- .5.1.2.1.1.10

ieee1588CmldsLinkPortDsDomainNumber OBJECT-TYPE
    SYNTAX       Unsigned32(0..255)
    MAX-ACCESS   read-only
    STATUS       current
    DESCRIPTION
        "The domainNumber used by this Link Port. This domain number is
        not configurable, since its value is determined by the transport
        mechanism of the Link Port. The value of sdoId is defined for
        CMLDS as constant with the value 0x200."
    REFERENCE    "IEEE 1588-2019: clause 16.6.4.2.2.2"
    ::= { ieee1588CmldsLinkPortDsEntry 11 }
-- .5.1.2.1.1.11

ieee1588CmldsTimestampCorrectionLinkPortDsTable OBJECT-TYPE
    SYNTAX   SEQUENCE OF Ieee1588CmldsTimestampCorrectionLinkPortDsEntry
    MAX-ACCESS   not-accessible
    STATUS       current
    DESCRIPTION
        "The cmldsTimestampCorrectionLinkPortDS data set with Timestamp
        Correction Link Port data for Common Mean Link Delay Service for
        a specific Link Port. This optional data set provides access to
        the configurable correction of generated timestamps."
    REFERENCE    "IEEE 1588-2019: clause 16.6.4.3, 8.2.16.1"
    ::= { ieee1588CmldsLinkPortList 2 }
-- .5.1.2.2

ieee1588CmldsTimestampCorrectionLinkPortDsEntry OBJECT-TYPE
    SYNTAX       Ieee1588CmldsTimestampCorrectionLinkPortDsEntry
    MAX-ACCESS   not-accessible
    STATUS       current
    DESCRIPTION
        "An Entry providing attributes of
        cmldsTimestampCorrectionLinkPortDS data set with Timestamp
        Correction Link Port data for Common Mean Link Delay Service for
        a specific Link Port."
    INDEX        {
        ieee1588LinkPortIndex }
    ::= { ieee1588CmldsTimestampCorrectionLinkPortDsTable 1 }
-- .5.1.2.2.1


Ieee1588CmldsTimestampCorrectionLinkPortDsEntry    ::= SEQUENCE {
        ieee1588CmldsTimestampCorrectionLinkPortDsEgressLatency
                                             Ieee1588TimeInterval,
        ieee1588CmldsTimestampCorrectionLinkPortDsIngressLatency
                                             Ieee1588TimeInterval
        }

ieee1588CmldsTimestampCorrectionLinkPortDsEgressLatency OBJECT-TYPE
    SYNTAX       Ieee1588TimeInterval
    UNITS        "scaled nanoseconds"
    MAX-ACCESS   read-write
    STATUS       current
    DESCRIPTION
        "Interval between the <egressProvidedTimestamp> provided for a
        PTP message and the time at which the message timestamp point of
        the PTP message crosses the reference plane."
    REFERENCE    "IEEE 1588-2019: clause 16.6.4.3.1, 8.2.16.2"
    ::= { ieee1588CmldsTimestampCorrectionLinkPortDsEntry 2 }
-- .5.1.2.2.1.2

ieee1588CmldsTimestampCorrectionLinkPortDsIngressLatency OBJECT-TYPE
    SYNTAX       Ieee1588TimeInterval
    UNITS        "scaled nanoseconds"
    MAX-ACCESS   read-write
    STATUS       current
    DESCRIPTION
        "Interval between the time the message timestamp point of an
        ingress PTP message crosses the reference plane and the
        <ingressProvidedTimestamp> provided for the PTP message."
    REFERENCE    "IEEE 1588-2019: clause 16.6.4.3.2, 8.2.16.3"
    ::= { ieee1588CmldsTimestampCorrectionLinkPortDsEntry 3 }
-- .5.1.2.2.1.3

ieee1588CmldsAsymmetryCorrectionLinkPortDsTable OBJECT-TYPE
    SYNTAX   SEQUENCE OF Ieee1588CmldsAsymmetryCorrectionLinkPortDsEntry
    MAX-ACCESS   not-accessible
    STATUS       current
    DESCRIPTION
        "The cmldsAsymmetryCorrectionLinkPortDS data set with Asymmetry
        Correction Link Port data for Common Mean Link Delay Service for
        a specific Link Port. This optional data set provides access to
        the delay asymmetry correction."
    REFERENCE    "IEEE 1588-2019: clause 16.6.4.4, 8.2.17.1"
    ::= { ieee1588CmldsLinkPortList 3 }
-- .5.1.2.3

ieee1588CmldsAsymmetryCorrectionLinkPortDsEntry OBJECT-TYPE
    SYNTAX       Ieee1588CmldsAsymmetryCorrectionLinkPortDsEntry
    MAX-ACCESS   not-accessible
    STATUS       current
    DESCRIPTION
        "An Entry providing attributes of
        cmldsAsymmetryCorrectionLinkPortDS data set with Asymmetry
        Correction Link Port data for Common Mean Link Delay Service for
        a specific Link Port."
    INDEX        {
        ieee1588LinkPortIndex }
    ::= { ieee1588CmldsAsymmetryCorrectionLinkPortDsTable 1 }
-- .5.1.2.3.1


Ieee1588CmldsAsymmetryCorrectionLinkPortDsEntry    ::= SEQUENCE {
        ieee1588CmldsAsymmetryCorrectionLinkPortDsEnable TruthValue,
        ieee1588CmldsAsymmetryCorrectionLinkPortDsConstantAsymmetry
                                             Ieee1588TimeInterval,
        ieee1588CmldsAsymmetryCorrectionLinkPortDsScaledDelayCoefficient
                                             Ieee1588RelativeDifference
        }

ieee1588CmldsAsymmetryCorrectionLinkPortDsEnable OBJECT-TYPE
    SYNTAX       TruthValue
    MAX-ACCESS   read-write
    STATUS       current
    DESCRIPTION
        "When this value is true, the mechanism to calculate
        <delayAsymmetry> for certain media is enabled on this Link Port.
        When false, this mechanism is disabled on this Link Port."
    REFERENCE    "IEEE 1588-2019: clause 16.6.4.4.3, 8.2.17.4, 16.8"
    ::= { ieee1588CmldsAsymmetryCorrectionLinkPortDsEntry 2 }
-- .5.1.2.3.1.2

ieee1588CmldsAsymmetryCorrectionLinkPortDsConstantAsymmetry OBJECT-TYPE
    SYNTAX       Ieee1588TimeInterval
    UNITS        "scaled nanoseconds"
    MAX-ACCESS   read-write
    STATUS       current
    DESCRIPTION
        "Constant asymmetry used to fine adjust the dynamically
        calculated value of <delayAsymmetry>, when the mechanism to
        calculate <delayAsymmetry> for certain media is enabled."
    REFERENCE    "IEEE 1588-2019: clause 16.6.4.4.1, 8.2.17.2, 16.8"
    ::= { ieee1588CmldsAsymmetryCorrectionLinkPortDsEntry 3 }
-- .5.1.2.3.1.3

ieee1588CmldsAsymmetryCorrectionLinkPortDsScaledDelayCoefficient
                                                             OBJECT-TYPE
    SYNTAX       Ieee1588RelativeDifference
    MAX-ACCESS   read-write
    STATUS       current
    DESCRIPTION
        "This is the <delayCoefficient> (alpha)."
    REFERENCE    "IEEE 1588-2019: clause 16.6.4.4.2, 8.2.17.3"
    ::= { ieee1588CmldsAsymmetryCorrectionLinkPortDsEntry 4 }
-- .5.1.2.3.1.4

ieee1588CmldsPerfMonPortDs
                   OBJECT IDENTIFIER ::= { ieee1588CmldsLinkPortList 4 }

ieee1588CmldsPerfMonPortDsRecordListPdTable OBJECT-TYPE
    SYNTAX       SEQUENCE OF Ieee1588CmldsPerfMonPortDsRecordListPdEntry
    MAX-ACCESS   not-accessible
    STATUS       current
    DESCRIPTION
        "Table with performance monitoring records of
        cmldsPerformanceMonitoringLinkPortDS data set for a specific
        Link Port that is using the peer-to-peer (P2P) delay mechanism.
        The list is organized as follows:
        - 97 15-minute measurement records, the current record at index
        0, followed by the most recent 96 records.
        - 2 24-hour measurement records, the current record at index 97,
        and the previous record at index 98.
        If a record is not implemented for a specific index, management
        does not return the record. For example, if only four 15-minute
        periods are implemented, a management request for non-existing
        record-list returns an error.
        If only some of the data is reported, the same index values are
        used. As an example, if only the 24-hour statistics are
        accessed, the indexes are still 97 and 98.
        If a specific parameter (e.g.
        ieee1588CmldsPerfMonPortDsRecordListPdMinMeanLinkDelay) is not
        implemented, management does not return the parameter (i.e.,
        error). Parameters that are invalid (not measured correctly)
        shall be indicated with one in all bits, except the most
        significant. This represents the largest positive value of
        time-interval, indicating a value outside the maximum range."
    REFERENCE    "IEEE 1588-2019: clause 16.6.4.5, J.5.2"
    ::= { ieee1588CmldsPerfMonPortDs 1 }
-- .5.1.2.4.1

ieee1588CmldsPerfMonPortDsRecordListPdEntry OBJECT-TYPE
    SYNTAX       Ieee1588CmldsPerfMonPortDsRecordListPdEntry
    MAX-ACCESS   not-accessible
    STATUS       current
    DESCRIPTION
        "An Entry representing a performance monitoring record of a
        cmldsPerformanceMonitoringLinkPortDS data set for a specific
        Link Port within PTP Node that is using the peer-to-peer (P2P)
        delay mechanism."
    INDEX        {
        ieee1588LinkPortIndex,
        ieee1588CmldsPerfMonPortDsRecordListPdIndex }
    ::= { ieee1588CmldsPerfMonPortDsRecordListPdTable 1 }
-- .5.1.2.4.1.1


Ieee1588CmldsPerfMonPortDsRecordListPdEntry    ::= SEQUENCE {
        ieee1588CmldsPerfMonPortDsRecordListPdIndex Unsigned32,
        ieee1588CmldsPerfMonPortDsRecordListPdPmTime TimeStamp,
        ieee1588CmldsPerfMonPortDsRecordListPdAverMeanLinkDelay
                                             Ieee1588TimeInterval,
        ieee1588CmldsPerfMonPortDsRecordListPdMinMeanLinkDelay
                                             Ieee1588TimeInterval,
        ieee1588CmldsPerfMonPortDsRecordListPdMaxMeanLinkDelay
                                             Ieee1588TimeInterval,
        ieee1588CmldsPerfMonPortDsRecordListPdStdDevMLinkDelay
                                             Ieee1588TimeInterval
        }

ieee1588CmldsPerfMonPortDsRecordListPdIndex OBJECT-TYPE
    SYNTAX       Unsigned32(0..98)
    MAX-ACCESS   not-accessible
    STATUS       current
    DESCRIPTION
        "Table index of a performance monitoring record in a
        cmldsPerformanceMonitoringLinkPortDS data set for a specific
        Link Port within PTP Node that is using the peer-to-peer (P2P)
        delay mechanism."
    REFERENCE    "IEEE 1588-2019: clause 16.6.4.5, J.5.2.1"
    ::= { ieee1588CmldsPerfMonPortDsRecordListPdEntry 2 }
-- .5.1.2.4.1.1.2

ieee1588CmldsPerfMonPortDsRecordListPdPmTime OBJECT-TYPE
    SYNTAX       TimeStamp
    MAX-ACCESS   read-only
    STATUS       current
    DESCRIPTION
        "This value indicates the time of the beginning of the
        measurement period."
    REFERENCE    "IEEE 1588-2019: clause 16.6.4.5, J.4.1, J.5.2.1"
    ::= { ieee1588CmldsPerfMonPortDsRecordListPdEntry 3 }
-- .5.1.2.4.1.1.3

ieee1588CmldsPerfMonPortDsRecordListPdAverMeanLinkDelay OBJECT-TYPE
    SYNTAX       Ieee1588TimeInterval
    UNITS        "scaled nanoseconds"
    MAX-ACCESS   read-only
    STATUS       current
    DESCRIPTION
        "Average of the meanLinkDelay for each 15 min or 24 h interval
        on specific Link Port that is using the peer-to-peer (P2P) delay
        mechanism."
    REFERENCE    "IEEE 1588-2019: clause 16.6.4.5, J.2, J.5.2.1"
    ::= { ieee1588CmldsPerfMonPortDsRecordListPdEntry 4 }
-- .5.1.2.4.1.1.4

ieee1588CmldsPerfMonPortDsRecordListPdMinMeanLinkDelay OBJECT-TYPE
    SYNTAX       Ieee1588TimeInterval
    UNITS        "scaled nanoseconds"
    MAX-ACCESS   read-only
    STATUS       current
    DESCRIPTION
        "Minimum of the meanLinkDelay for each 15 min or 24 h interval
        on specific Link Port that is using the peer-to-peer (P2P) delay
        mechanism."
    REFERENCE    "IEEE 1588-2019: clause 16.6.4.5, J.2, J.5.2.1"
    ::= { ieee1588CmldsPerfMonPortDsRecordListPdEntry 5 }
-- .5.1.2.4.1.1.5

ieee1588CmldsPerfMonPortDsRecordListPdMaxMeanLinkDelay OBJECT-TYPE
    SYNTAX       Ieee1588TimeInterval
    UNITS        "scaled nanoseconds"
    MAX-ACCESS   read-only
    STATUS       current
    DESCRIPTION
        "Maximum of the meanLinkDelay for each 15 min or 24 h interval
        on specific Link Port that is using the peer-to-peer (P2P) delay
        mechanism."
    REFERENCE    "IEEE 1588-2019: clause 16.6.4.5, J.2, J.5.2.1"
    ::= { ieee1588CmldsPerfMonPortDsRecordListPdEntry 6 }
-- .5.1.2.4.1.1.6

ieee1588CmldsPerfMonPortDsRecordListPdStdDevMLinkDelay OBJECT-TYPE
    SYNTAX       Ieee1588TimeInterval
    UNITS        "scaled nanoseconds"
    MAX-ACCESS   read-only
    STATUS       current
    DESCRIPTION
        "Standard deviation of the meanLinkDelay for each 15 min or 24 h
        interval on specific Link Port that is using the peer-to-peer
        (P2P) delay mechanism."
    REFERENCE    "IEEE 1588-2019: clause 16.6.4.5, J.2, J.5.2.1"
    ::= { ieee1588CmldsPerfMonPortDsRecordListPdEntry 7 }
-- .5.1.2.4.1.1.7

ieee1588CmldsPerfMonPortDsRecordListTable OBJECT-TYPE
    SYNTAX       SEQUENCE OF Ieee1588CmldsPerfMonPortDsRecordListEntry
    MAX-ACCESS   not-accessible
    STATUS       current
    DESCRIPTION
        "Table with performance monitoring records of
        cmldsPerformanceMonitoringLinkPortDS data set not specific to
        the peer-to-peer delay measurement mechanism for a specific Link
        Port within PTP Node. The list is organized as follows:
        - 97 15-minute measurement records, the current record at index
        0, followed by the most recent 96 records.
        - 2 24-hour measurement records, the current record at index 97,
        and the previous record at index 98.
        If a record is not implemented for a specific index, management
        does not return the record. For example, if only four 15-minute
        periods are implemented, a management request for non-existing
        record-list returns an error.
        If only some of the data is reported, the same index values are
        used. As an example, if only the 24-hour statistics are
        accessed, the indexes are still 97 and 98.
        If a specific parameter (e.g. sync-tx) is not implemented,
        management does not return the parameter (i.e., error).
        Parameters that are invalid (not measured correctly) shall be
        indicated with with the value zero, indicating that nothing was
        counted.
        Each counter in the record shall be initialized to zero at the
        start of a new 15-minute and 24-hour interval."
    REFERENCE    "IEEE 1588-2019: clause J.5.2"
    ::= { ieee1588CmldsPerfMonPortDs 2 }
-- .5.1.2.4.2

ieee1588CmldsPerfMonPortDsRecordListEntry OBJECT-TYPE
    SYNTAX       Ieee1588CmldsPerfMonPortDsRecordListEntry
    MAX-ACCESS   not-accessible
    STATUS       current
    DESCRIPTION
        "An Entry representing a performance monitoring record of a
        cmldsPerformanceMonitoringLinkPortDS data set for a specific
        Link Port."
    INDEX        {
        ieee1588LinkPortIndex,
        ieee1588CmldsPerfMonPortDsRecordListIndex }
    ::= { ieee1588CmldsPerfMonPortDsRecordListTable 1 }
-- .5.1.2.4.2.1


Ieee1588CmldsPerfMonPortDsRecordListEntry    ::= SEQUENCE {
        ieee1588CmldsPerfMonPortDsRecordListIndex Unsigned32,
        ieee1588CmldsPerfMonPortDsRecordListPmTime TimeStamp,
        ieee1588CmldsPerfMonPortDsRecordListAnnounceTx Counter32,
        ieee1588CmldsPerfMonPortDsRecordListAnnounceRx Counter32,
        ieee1588CmldsPerfMonPortDsRecordListAnnounceFMasterRx Counter32,
        ieee1588CmldsPerfMonPortDsRecordListSyncTx Counter32,
        ieee1588CmldsPerfMonPortDsRecordListSyncRx Counter32,
        ieee1588CmldsPerfMonPortDsRecordListFollowUpTx Counter32,
        ieee1588CmldsPerfMonPortDsRecordListFollowUpRx Counter32,
        ieee1588CmldsPerfMonPortDsRecordListDelayReqTx Counter32,
        ieee1588CmldsPerfMonPortDsRecordListDelayReqRx Counter32,
        ieee1588CmldsPerfMonPortDsRecordListDelayRespTx Counter32,
        ieee1588CmldsPerfMonPortDsRecordListDelayRespRx Counter32,
        ieee1588CmldsPerfMonPortDsRecordListPDelayReqTx Counter32,
        ieee1588CmldsPerfMonPortDsRecordListPDelayReqRx Counter32,
        ieee1588CmldsPerfMonPortDsRecordListPDelayRespTx Counter32,
        ieee1588CmldsPerfMonPortDsRecordListPDelayRespRx Counter32,
        ieee1588CmldsPerfMonPortDsRecordListPDelayRespFollowUpTx
                                             Counter32,
        ieee1588CmldsPerfMonPortDsRecordListPDelayRespFollowUpRx
                                             Counter32
        }

ieee1588CmldsPerfMonPortDsRecordListIndex OBJECT-TYPE
    SYNTAX       Unsigned32(0..98)
    MAX-ACCESS   not-accessible
    STATUS       current
    DESCRIPTION
        "Table index of a performance monitoring record in a
        cmldsPerformanceMonitoringLinkPortDS data set for a specific
        Link Port."
    REFERENCE    "IEEE 1588-2019: clause 16.6.4.5, J.5.2.1"
    ::= { ieee1588CmldsPerfMonPortDsRecordListEntry 2 }
-- .5.1.2.4.2.1.2

ieee1588CmldsPerfMonPortDsRecordListPmTime OBJECT-TYPE
    SYNTAX       TimeStamp
    MAX-ACCESS   read-only
    STATUS       current
    DESCRIPTION
        "This value indicates the time of the beginning of the
        measurement period."
    REFERENCE    "IEEE 1588-2019: clause 16.6.4.5, J.4.1, J.5.2.1"
    ::= { ieee1588CmldsPerfMonPortDsRecordListEntry 3 }
-- .5.1.2.4.2.1.3

ieee1588CmldsPerfMonPortDsRecordListAnnounceTx OBJECT-TYPE
    SYNTAX       Counter32
    UNITS        "messages"
    MAX-ACCESS   read-only
    STATUS       current
    DESCRIPTION
        "Counter indicating the number of Announce messages that have
        been transmitted for each 15 min or 24 h interval on specific
        Link Port."
    REFERENCE    "IEEE 1588-2019: clause 16.6.4.5, J.2, J.5.2.2"
    ::= { ieee1588CmldsPerfMonPortDsRecordListEntry 4 }
-- .5.1.2.4.2.1.4

ieee1588CmldsPerfMonPortDsRecordListAnnounceRx OBJECT-TYPE
    SYNTAX       Counter32
    UNITS        "messages"
    MAX-ACCESS   read-only
    STATUS       current
    DESCRIPTION
        "Counter indicating the number of Announce messages from the
        current GM that have been received for each 15 min or 24 h
        interval on specific Link Port."
    REFERENCE    "IEEE 1588-2019: clause 16.6.4.5, J.2, J.5.2.2"
    ::= { ieee1588CmldsPerfMonPortDsRecordListEntry 5 }
-- .5.1.2.4.2.1.5

ieee1588CmldsPerfMonPortDsRecordListAnnounceFMasterRx OBJECT-TYPE
    SYNTAX       Counter32
    UNITS        "messages"
    MAX-ACCESS   read-only
    STATUS       current
    DESCRIPTION
        "Counter indicating the total number of Announce messages from
        the foreign Masters that have been received for each 15 min or
        24 h interval on specific Link Port."
    REFERENCE    "IEEE 1588-2019: clause 16.6.4.5, J.2, J.5.2.2"
    ::= { ieee1588CmldsPerfMonPortDsRecordListEntry 6 }
-- .5.1.2.4.2.1.6

ieee1588CmldsPerfMonPortDsRecordListSyncTx OBJECT-TYPE
    SYNTAX       Counter32
    UNITS        "messages"
    MAX-ACCESS   read-only
    STATUS       current
    DESCRIPTION
        "Counter indicating the number of Sync messages that have been
        transmitted for each 15 min or 24 h interval on specific Link
        Port."
    REFERENCE    "IEEE 1588-2019: clause 16.6.4.5, J.2, J.5.2.2"
    ::= { ieee1588CmldsPerfMonPortDsRecordListEntry 7 }
-- .5.1.2.4.2.1.7

ieee1588CmldsPerfMonPortDsRecordListSyncRx OBJECT-TYPE
    SYNTAX       Counter32
    UNITS        "messages"
    MAX-ACCESS   read-only
    STATUS       current
    DESCRIPTION
        "Counter indicating the number of Sync messages that have been
        received for each 15 min or 24 h interval on specific Link
        Port."
    REFERENCE    "IEEE 1588-2019: clause 16.6.4.5, J.2, J.5.2.2"
    ::= { ieee1588CmldsPerfMonPortDsRecordListEntry 8 }
-- .5.1.2.4.2.1.8

ieee1588CmldsPerfMonPortDsRecordListFollowUpTx OBJECT-TYPE
    SYNTAX       Counter32
    UNITS        "messages"
    MAX-ACCESS   read-only
    STATUS       current
    DESCRIPTION
        "Counter indicating the number of Follow_Up messages that have
        been transmitted for each 15 min or 24 h interval on specific
        Link Port."
    REFERENCE    "IEEE 1588-2019: clause 16.6.4.5, J.2, J.5.2.2"
    ::= { ieee1588CmldsPerfMonPortDsRecordListEntry 9 }
-- .5.1.2.4.2.1.9

ieee1588CmldsPerfMonPortDsRecordListFollowUpRx OBJECT-TYPE
    SYNTAX       Counter32
    UNITS        "messages"
    MAX-ACCESS   read-only
    STATUS       current
    DESCRIPTION
        "Counter indicating the number of Follow_Up messages that have
        been received for each 15 min or 24 h interval on specific Link
        Port."
    REFERENCE    "IEEE 1588-2019: clause 16.6.4.5, J.2, J.5.2.2"
    ::= { ieee1588CmldsPerfMonPortDsRecordListEntry 10 }
-- .5.1.2.4.2.1.10

ieee1588CmldsPerfMonPortDsRecordListDelayReqTx OBJECT-TYPE
    SYNTAX       Counter32
    UNITS        "messages"
    MAX-ACCESS   read-only
    STATUS       current
    DESCRIPTION
        "Counter indicating the number of Delay_Req messages that have
        been transmitted for each 15 min or 24 h interval on specific
        Link Port."
    REFERENCE    "IEEE 1588-2019: clause 16.6.4.5, J.2, J.5.2.2"
    ::= { ieee1588CmldsPerfMonPortDsRecordListEntry 11 }
-- .5.1.2.4.2.1.11

ieee1588CmldsPerfMonPortDsRecordListDelayReqRx OBJECT-TYPE
    SYNTAX       Counter32
    UNITS        "messages"
    MAX-ACCESS   read-only
    STATUS       current
    DESCRIPTION
        "Counter indicating the number of Delay_Req messages that have
        been received for each 15 min or 24 h interval on specific Link
        Port."
    REFERENCE    "IEEE 1588-2019: clause 16.6.4.5, J.2, J.5.2.2"
    ::= { ieee1588CmldsPerfMonPortDsRecordListEntry 12 }
-- .5.1.2.4.2.1.12

ieee1588CmldsPerfMonPortDsRecordListDelayRespTx OBJECT-TYPE
    SYNTAX       Counter32
    UNITS        "messages"
    MAX-ACCESS   read-only
    STATUS       current
    DESCRIPTION
        "Counter indicating the number of Delay_Resp messages that have
        been transmitted for each 15 min or 24 h interval on specific
        Link Port."
    REFERENCE    "IEEE 1588-2019: clause 16.6.4.5, J.2, J.5.2.2"
    ::= { ieee1588CmldsPerfMonPortDsRecordListEntry 13 }
-- .5.1.2.4.2.1.13

ieee1588CmldsPerfMonPortDsRecordListDelayRespRx OBJECT-TYPE
    SYNTAX       Counter32
    UNITS        "messages"
    MAX-ACCESS   read-only
    STATUS       current
    DESCRIPTION
        "Counter indicating the number of Delay_Resp messages that have
        been received for each 15 min or 24 h interval on specific Link
        Port."
    REFERENCE    "IEEE 1588-2019: clause 16.6.4.5, J.2, J.5.2.2"
    ::= { ieee1588CmldsPerfMonPortDsRecordListEntry 14 }
-- .5.1.2.4.2.1.14

ieee1588CmldsPerfMonPortDsRecordListPDelayReqTx OBJECT-TYPE
    SYNTAX       Counter32
    UNITS        "messages"
    MAX-ACCESS   read-only
    STATUS       current
    DESCRIPTION
        "Counter indicating the number of Pdelay_Req messages that have
        been transmitted for each 15 min or 24 h interval on specific
        Link Port."
    REFERENCE    "IEEE 1588-2019: clause 16.6.4.5, J.2, J.5.2.2"
    ::= { ieee1588CmldsPerfMonPortDsRecordListEntry 15 }
-- .5.1.2.4.2.1.15

ieee1588CmldsPerfMonPortDsRecordListPDelayReqRx OBJECT-TYPE
    SYNTAX       Counter32
    UNITS        "messages"
    MAX-ACCESS   read-only
    STATUS       current
    DESCRIPTION
        "Counter indicating the number of Pdelay_Req messages that have
        been received for each 15 min or 24 h interval on specific Link
        Port."
    REFERENCE    "IEEE 1588-2019: clause 16.6.4.5, J.2, J.5.2.2"
    ::= { ieee1588CmldsPerfMonPortDsRecordListEntry 16 }
-- .5.1.2.4.2.1.16

ieee1588CmldsPerfMonPortDsRecordListPDelayRespTx OBJECT-TYPE
    SYNTAX       Counter32
    UNITS        "messages"
    MAX-ACCESS   read-only
    STATUS       current
    DESCRIPTION
        "Counter indicating the number of Pdelay_Resp messages that have
        been transmitted for each 15 min or 24 h interval on specific
        Link Port."
    REFERENCE    "IEEE 1588-2019: clause 16.6.4.5, J.2, J.5.2.2"
    ::= { ieee1588CmldsPerfMonPortDsRecordListEntry 17 }
-- .5.1.2.4.2.1.17

ieee1588CmldsPerfMonPortDsRecordListPDelayRespRx OBJECT-TYPE
    SYNTAX       Counter32
    UNITS        "messages"
    MAX-ACCESS   read-only
    STATUS       current
    DESCRIPTION
        "Counter indicating the number of Pdelay_Resp messages that have
        been received for each 15 min or 24 h interval on specific Link
        Port."
    REFERENCE    "IEEE 1588-2019: clause 16.6.4.5, J.2, J.5.2.2"
    ::= { ieee1588CmldsPerfMonPortDsRecordListEntry 18 }
-- .5.1.2.4.2.1.18

ieee1588CmldsPerfMonPortDsRecordListPDelayRespFollowUpTx OBJECT-TYPE
    SYNTAX       Counter32
    UNITS        "messages"
    MAX-ACCESS   read-only
    STATUS       current
    DESCRIPTION
        "Counter indicating the number of Pdelay_Resp_Follow_Up messages
        that have been transmitted for each 15 min or 24 h interval on
        specific Link Port."
    REFERENCE    "IEEE 1588-2019: clause 16.6.4.5, J.2, J.5.2.2"
    ::= { ieee1588CmldsPerfMonPortDsRecordListEntry 19 }
-- .5.1.2.4.2.1.19

ieee1588CmldsPerfMonPortDsRecordListPDelayRespFollowUpRx OBJECT-TYPE
    SYNTAX       Counter32
    UNITS        "messages"
    MAX-ACCESS   read-only
    STATUS       current
    DESCRIPTION
        "Counter indicating the number of Pdelay_Resp_Follow_Up messages
        that have been received for each 15 min or 24 h interval on
        specific Link Port."
    REFERENCE    "IEEE 1588-2019: clause 16.6.4.5, J.2, J.5.2.2"
    ::= { ieee1588CmldsPerfMonPortDsRecordListEntry 20 }
-- .5.1.2.4.2.1.20

-- ieee1588Profiles branch is intentionally kept empty in this MIB.
-- This is a placeholder that can be used by PTP Profiles. It is
-- expected that the IEEE1588 MIB is used and extended by PTP Profiles
-- defined outside of the IEEE 1588 standard. A PTP Profile defined
-- outside of this standard can use this MIB as is, if such a profile
-- does not define any additional data set members or enumeration
-- values. If a PTP Profile defines profile-specific information that
-- needs to be mapped into MIB, it should define a profile-specific MIB
-- that includes only the profile-specific information and its structure
-- is placed under the following base:
-- ieee1588Profiles.mibProfileID, where mibProfileID is a single 32bit
-- value that contains 4 most significant octets of the
-- profileIdentifier (see IEEE Std 1588 20.3.3), i.e. the most
-- significant 3 octets is either an OUI or a CID owned by the
-- organization creating the profile, the next octet is the
-- profileNumber.
-- For more information see IEEE Std 1588-2019 as amended by IEEE Std
-- 1588e, 15.3.3.15. Numeric ID of profiles will be defined at
-- https://sagroups.ieee.org/1588/ptp-profiles/
ieee1588Profiles OBJECT IDENTIFIER ::= { ieee1588Objects 6 }

--=====================================================================
-- Conformance Information
--=====================================================================

ieee1588Conformance OBJECT IDENTIFIER ::= { ieee1588MibV1 2 }
ieee1588Groups OBJECT IDENTIFIER ::= { ieee1588Conformance 1 }
ieee1588AcceptableMasterPortDsGrp  OBJECT-GROUP
    OBJECTS {
        ieee1588AcceptableMasterPortDsEnable
        }
    STATUS       current
    DESCRIPTION
        "Objects in the Acceptable Master Port Data Set"
    ::= { ieee1588Groups 1 }


ieee1588AcceptableMasterTableDsGrp  OBJECT-GROUP
    OBJECTS {
        ieee1588AcceptableMasterTableDsMaxTableSize,
        ieee1588AcceptableMasterTableDsListRowStatus,
        ieee1588AcceptableMasterTableDsListAccPortIdentityClockIdentity,
        ieee1588AcceptableMasterTableDsListAccPortIdentityPortNumber,
        ieee1588AcceptableMasterTableDsListAlternatePriority1
        }
    STATUS       current
    DESCRIPTION
        "Objects in the Acceptable Master Table Data Set"
    ::= { ieee1588Groups 2 }


ieee1588AlternateMasterPortDsGrp  OBJECT-GROUP
    OBJECTS {
        ieee1588AlternateMasterPortDsNumberOfAlternateMasters,
        ieee1588AlternateMasterPortDsTransmitAlternateMulticastSync,
        ieee1588AlternateMasterPortDsLogAlternateMulticastSyncInterval
        }
    STATUS       current
    DESCRIPTION
        "Objects in the Alternate Master Port Data Set"
    ::= { ieee1588Groups 3 }


ieee1588AlternateTimeScaleOffsetDsGrp  OBJECT-GROUP
    OBJECTS {
        ieee1588AlternateTimeScaleOffsetDsMaxKey,
        ieee1588AlternateTimeScaleOffsetDsListRowStatus,
        ieee1588AlternateTimeScaleOffsetDsListKeyField,
        ieee1588AlternateTimeScaleOffsetDsListEnable,
        ieee1588AlternateTimeScaleOffsetDsListCurrentOffset,
        ieee1588AlternateTimeScaleOffsetDsListJumpSeconds,
        ieee1588AlternateTimeScaleOffsetDsListTimeOfNextJump,
        ieee1588AlternateTimeScaleOffsetDsListDisplayName,
        ieee1588GrandmasterClusterDsPortAddressRowStatus
        }
    STATUS       current
    DESCRIPTION
        "Objects in the Alternate Time Scale Offset Data Set"
    ::= { ieee1588Groups 4 }


ieee1588AsymmetryCorrectionPortDsGrp  OBJECT-GROUP
    OBJECTS {
        ieee1588AsymmetryCorrectionPortDsEnable,
        ieee1588AsymmetryCorrectionPortDsConstantAsymmetry,
        ieee1588AsymmetryCorrectionPortDsScaledDelayCoefficient
        }
    STATUS       current
    DESCRIPTION
        "Objects in the Asymmetry Correction Port Data Set"
    ::= { ieee1588Groups 5 }


ieee1588BaseInstanceGrp  OBJECT-GROUP
    OBJECTS {
        ieee1588BaseInstanceRowStatus,
        ieee1588BaseInstanceName,
        ieee1588BasePortRowStatus
        }
    STATUS       current
    DESCRIPTION
        "Objects in the Base Instance"
    ::= { ieee1588Groups 6 }


ieee1588BasePortGrp  OBJECT-GROUP
    OBJECTS {
        ieee1588BasePortIfIndex,
        ieee1588BasePortIfIndexOid
        }
    STATUS       current
    DESCRIPTION
        "Objects in the Base Port"
    ::= { ieee1588Groups 7 }


ieee1588CmldsAsymmetryCorrectionLinkPortDsGrp  OBJECT-GROUP
    OBJECTS {
        ieee1588CmldsAsymmetryCorrectionLinkPortDsEnable,
        ieee1588CmldsAsymmetryCorrectionLinkPortDsConstantAsymmetry,
        ieee1588CmldsAsymmetryCorrectionLinkPortDsScaledDelayCoefficient
        }
    STATUS       current
    DESCRIPTION
        "Objects in the Common Mean Link Delay Service Asymmetry
        Correction Link Port Data Set"
    ::= { ieee1588Groups 8 }


ieee1588CmldsDefaultDsGrp  OBJECT-GROUP
    OBJECTS {
        ieee1588CmldsDefaultDsClockIdentity,
        ieee1588CmldsDefaultDsNumberLinkPorts
        }
    STATUS       deprecated
    DESCRIPTION
        "Deprecated objects in the Common Mean Link Delay Service
        Default Data Set"
    ::= { ieee1588Groups 9 }


ieee1588CmldsLinkPortDsGrp  OBJECT-GROUP
    OBJECTS {
        ieee1588CmldsLinkPortDsPortIdentityClockIdentity,
        ieee1588CmldsLinkPortDsPortIdentityPortNumber,
        ieee1588CmldsLinkPortDsCmldiServiceMeasurementValid,
        ieee1588CmldsLinkPortDsCmldiMeanLinkDelay,
        ieee1588CmldsLinkPortDsCmldiScaledNeighborRateRatio,
        ieee1588CmldsLinkPortDsLogMinPdelayReqInterval,
        ieee1588CmldsLinkPortDsVersionNumber,
        ieee1588CmldsLinkPortDsMinorVersionNumber,
        ieee1588CmldsLinkPortDsDelayAsymmetry,
        ieee1588CmldsLinkPortDsDomainNumber
        }
    STATUS       current
    DESCRIPTION
        "Objects in the Common Mean Link Delay Service Link Port Data
        Set"
    ::= { ieee1588Groups 10 }


ieee1588CmldsTimestampCorrectionLinkPortDsGrp  OBJECT-GROUP
    OBJECTS {
        ieee1588CmldsTimestampCorrectionLinkPortDsEgressLatency,
        ieee1588CmldsTimestampCorrectionLinkPortDsIngressLatency
        }
    STATUS       current
    DESCRIPTION
        "Objects in the Common Mean Link Delay Service Timestamp
        Correction Link Port Data Set"
    ::= { ieee1588Groups 11 }


ieee1588CommonServicesPortDsGrp  OBJECT-GROUP
    OBJECTS {
        ieee1588CommonServicesPortDsCmldsLinkPortPortNumber
        }
    STATUS       current
    DESCRIPTION
        "Objects in the Common Services Port Data Set"
    ::= { ieee1588Groups 12 }


ieee1588CommunicationCapabilitiesPortDsGrp  OBJECT-GROUP
    OBJECTS {
        ieee1588CommunicationCapabilitiesPortDsSyncCapMulticastCap,
        ieee1588CommunicationCapabilitiesPortDsSyncCapUnicastCap,
        ieee1588CommunicationCapabilitiesPortDsSyncCapUnicastNegCap,
        ieee1588CommunicationCapabilitiesPortDsSyncCapUnicastNegReq,
        ieee1588CommunicationCapabilitiesPortDsDelayRespCapMulticastCap,
        ieee1588CommunicationCapabilitiesPortDsDelayRespCapUnicastCap,
        ieee1588CommunicationCapabilitiesPortDsDelayRespCapUnicastNegCap,
        ieee1588CommunicationCapabilitiesPortDsDelayRespCapUnicastNegReq
        }
    STATUS       current
    DESCRIPTION
        "Objects in the Communication Capabilities Port Data Set"
    ::= { ieee1588Groups 13 }


ieee1588CurrentDsGrp  OBJECT-GROUP
    OBJECTS {
        ieee1588CurrentDsStepsRemoved,
        ieee1588CurrentDsOffsetFromMaster,
        ieee1588CurrentDsMeanDelay,
        ieee1588CurrentDsSyncUncertain
        }
    STATUS       current
    DESCRIPTION
        "Objects in the Current Data Set"
    ::= { ieee1588Groups 14 }


ieee1588DefaultDsDeprecatedGrp  OBJECT-GROUP
    OBJECTS {
        ieee1588DefaultDsTwoStepFlag
        }
    STATUS       deprecated
    DESCRIPTION
        "Deprecated objects in Default Data Set"
    ::= { ieee1588Groups 15 }


ieee1588DefaultDsGrp  OBJECT-GROUP
    OBJECTS {
        ieee1588DefaultDsClockIdentity,
        ieee1588DefaultDsNumberPorts,
        ieee1588DefaultDsClockQualityClockClass,
        ieee1588DefaultDsClockQualityClockAccuracy,
        ieee1588DefaultDsClockQualityOffsetScaledLogVariance,
        ieee1588DefaultDsPriority1,
        ieee1588DefaultDsPriority2,
        ieee1588DefaultDsDomainNumber,
        ieee1588DefaultDsSlaveOnly,
        ieee1588DefaultDsSdoId,
        ieee1588DefaultDsCurrentTimeSecondsField,
        ieee1588DefaultDsCurrentTimeNanosecondsField,
        ieee1588DefaultDsInstanceEnable,
        ieee1588DefaultDsExternalPortConfigurationEnabled,
        ieee1588DefaultDsMaxStepsRemoved,
        ieee1588DefaultDsInstanceType
        }
    STATUS       current
    DESCRIPTION
        "Objects in the Default Data Set"
    ::= { ieee1588Groups 16 }


ieee1588DescriptionDsGrp  OBJECT-GROUP
    OBJECTS {
        ieee1588DescriptionDsManufacturerIdentity,
        ieee1588DescriptionDsProductDescription,
        ieee1588DescriptionDsProductRevision,
        ieee1588DescriptionDsUserDescription
        }
    STATUS       current
    DESCRIPTION
        "Objects in the Description Data Set"
    ::= { ieee1588Groups 17 }


ieee1588DescriptionPortDsGrp  OBJECT-GROUP
    OBJECTS {
        ieee1588DescriptionPortDsProfileIdentifier,
        ieee1588DescriptionPortDsProtocolAddressNetworkProtocol,
        ieee1588DescriptionPortDsProtocolAddressAddressLength,
        ieee1588DescriptionPortDsProtocolAddressAddressField
        }
    STATUS       current
    DESCRIPTION
        "Objects in the Description Port Data Set"
    ::= { ieee1588Groups 18 }


ieee1588EnhancedSynchronizationAccuracyMetricsDsGrp  OBJECT-GROUP
    OBJECTS {
        ieee1588EnhancedSynchronizationAccuracyMetricsDsEnable
        }
    STATUS       current
    DESCRIPTION
        "Objects in the Enhanced Synchronization Accuracy Metrics Data
        Set"
    ::= { ieee1588Groups 19 }


ieee1588ExternalPortConfigurationPortDsGrp  OBJECT-GROUP
    OBJECTS {
        ieee1588ExternalPortConfigurationPortDsDesiredState
        }
    STATUS       current
    DESCRIPTION
        "Objects in the External Port Configuration Port Data Set"
    ::= { ieee1588Groups 20 }


ieee1588FaultLogDsGrp  OBJECT-GROUP
    OBJECTS {
        ieee1588FaultLogDsNumberOfFaultRecords,
        ieee1588FaultLogDsReset,
        ieee1588FaultLogDsFaultRecordListFaultTimeSecondsField,
        ieee1588FaultLogDsFaultRecordListFaultTimeNanosecondsField,
        ieee1588FaultLogDsFaultRecordListSeverityCode,
        ieee1588FaultLogDsFaultRecordListFaultName,
        ieee1588FaultLogDsFaultRecordListFaultValue,
        ieee1588FaultLogDsFaultRecordListFaultDescription
        }
    STATUS       current
    DESCRIPTION
        "Objects in the Fault Log Data Set"
    ::= { ieee1588Groups 21 }


ieee1588GrandmasterClusterDsGrp  OBJECT-GROUP
    OBJECTS {
        ieee1588GrandmasterClusterDsMaxTableSize,
        ieee1588GrandmasterClusterDsLogQueryInterval,
        ieee1588GrandmasterClusterDsPortAddressNetworkProtocol,
        ieee1588GrandmasterClusterDsPortAddressAddressLength,
        ieee1588GrandmasterClusterDsPortAddressAddressField
        }
    STATUS       current
    DESCRIPTION
        "Objects in the Grandmaster Cluster Data Set"
    ::= { ieee1588Groups 22 }


ieee1588HoldoverUpgradeDsGrp  OBJECT-GROUP
    OBJECTS {
        ieee1588HoldoverUpgradeDsEnable
        }
    STATUS       current
    DESCRIPTION
        "Objects in the Holdover Upgrade Data Set"
    ::= { ieee1588Groups 23 }


ieee1588L1SyncBasicPortDsGrp  OBJECT-GROUP
    OBJECTS {
        ieee1588L1SyncBasicPortDsL1SyncEnabled,
        ieee1588L1SyncBasicPortDsTxCoherentIsRequired,
        ieee1588L1SyncBasicPortDsRxCoherentIsRequired,
        ieee1588L1SyncBasicPortDsCongruentIsRequired,
        ieee1588L1SyncBasicPortDsOptParamsEnabled,
        ieee1588L1SyncBasicPortDsLogL1SyncInterval,
        ieee1588L1SyncBasicPortDsL1SyncReceiptTimeout,
        ieee1588L1SyncBasicPortDsL1SyncLinkAlive,
        ieee1588L1SyncBasicPortDsIsTxCoherent,
        ieee1588L1SyncBasicPortDsIsRxCoherent,
        ieee1588L1SyncBasicPortDsIsCongruent,
        ieee1588L1SyncBasicPortDsL1SyncState,
        ieee1588L1SyncBasicPortDsPeerTxCoherentIsRequired,
        ieee1588L1SyncBasicPortDsPeerRxCoherentIsRequired,
        ieee1588L1SyncBasicPortDsPeerCongruentIsRequired,
        ieee1588L1SyncBasicPortDsPeerIsTxCoherent,
        ieee1588L1SyncBasicPortDsPeerIsRxCoherent,
        ieee1588L1SyncBasicPortDsPeerIsCongruent
        }
    STATUS       current
    DESCRIPTION
        "Objects in the L1 Sync Basic Port Data Set"
    ::= { ieee1588Groups 24 }


ieee1588L1SyncOptParamsPortDsGrp  OBJECT-GROUP
    OBJECTS {
        ieee1588L1SyncOptParamsPortDsTimestampsCorrectedTx,
        ieee1588L1SyncOptParamsPortDsPhaseOffsetTxValid,
        ieee1588L1SyncOptParamsPortDsFrequencyOffsetTxValid,
        ieee1588L1SyncOptParamsPortDsPhaseOffsetTx,
        ieee1588L1SyncOptParamsPortDsPhaseOffsetTxTsSecondsField,
        ieee1588L1SyncOptParamsPortDsPhaseOffsetTxTsNanosecondsField,
        ieee1588L1SyncOptParamsPortDsFrequencyOffsetTx,
        ieee1588L1SyncOptParamsPortDsFrequencyOffsetTxTsSecondsField,
        ieee1588L1SyncOptParamsPortDsFrequencyOffsetTxTsNanosecondsField
        }
    STATUS       current
    DESCRIPTION
        "Objects in the L1 Sync Opt Params Port Data Set"
    ::= { ieee1588Groups 25 }


ieee1588NonVolatileStorageDsGrp  OBJECT-GROUP
    OBJECTS {
        ieee1588NonVolatileStorageDsReset,
        ieee1588NonVolatileStorageDsSave
        }
    STATUS       current
    DESCRIPTION
        "Objects in the Non Volatile Storage Data Set"
    ::= { ieee1588Groups 26 }


ieee1588ParentDsGrp  OBJECT-GROUP
    OBJECTS {
        ieee1588ParentDsParentPortIdentityClockIdentity,
        ieee1588ParentDsParentPortIdentityPortNumber,
        ieee1588ParentDsParentStats,
        ieee1588ParentDsObservedParentOffsetScaledLogVariance,
        ieee1588ParentDsObservedParentClockPhaseChangeRate,
        ieee1588ParentDsGrandmasterIdentity,
        ieee1588ParentDsGrandmasterClockQualityClockClass,
        ieee1588ParentDsGrandmasterClockQualityClockAccuracy,
        ieee1588ParentDsGrandmasterClockQualityOffsetScaledLogVariance,
        ieee1588ParentDsGrandmasterPriority1,
        ieee1588ParentDsGrandmasterPriority2,
        ieee1588ParentDsProtocolAddressNetworkProtocol,
        ieee1588ParentDsProtocolAddressAddressLength,
        ieee1588ParentDsProtocolAddressAddressField,
        ieee1588ParentDsSynchronizationUncertain
        }
    STATUS       current
    DESCRIPTION
        "Objects in the Parent Data Set"
    ::= { ieee1588Groups 27 }


ieee1588PathTraceDsGrp  OBJECT-GROUP
    OBJECTS {
        ieee1588PathTraceDsEnable,
        ieee1588PathTraceDsListClockIdentity
        }
    STATUS       current
    DESCRIPTION
        "Objects in the Path Trace Data Set"
    ::= { ieee1588Groups 28 }


ieee1588PerfMonDsGrp  OBJECT-GROUP
    OBJECTS {
        ieee1588PerfMonDsEnable,
        ieee1588PerfMonDsRecordListMeasurementValid,
        ieee1588PerfMonDsRecordListPeriodComplete,
        ieee1588PerfMonDsRecordListPmTime,
        ieee1588PerfMonDsRecordListAverageMasterSlaveDelay,
        ieee1588PerfMonDsRecordListMinMasterSlaveDelay,
        ieee1588PerfMonDsRecordListMaxMasterSlaveDelay,
        ieee1588PerfMonDsRecordListStdDevMasterSlaveDelay,
        ieee1588PerfMonDsRecordListAverageSlaveMasterDelay,
        ieee1588PerfMonDsRecordListMinSlaveMasterDelay,
        ieee1588PerfMonDsRecordListMaxSlaveMasterDelay,
        ieee1588PerfMonDsRecordListStdDevSlaveMasterDelay,
        ieee1588PerfMonDsRecordListAverageMeanPathDelay,
        ieee1588PerfMonDsRecordListMinMeanPathDelay,
        ieee1588PerfMonDsRecordListMaxMeanPathDelay,
        ieee1588PerfMonDsRecordListStdDevMeanPathDelay,
        ieee1588PerfMonDsRecordListAverageOffsetFromMaster,
        ieee1588PerfMonDsRecordListMinOffsetFromMaster,
        ieee1588PerfMonDsRecordListMaxOffsetFromMaster,
        ieee1588PerfMonDsRecordListStdDevOffsetFromMaster
        }
    STATUS       current
    DESCRIPTION
        "Objects in the Performance Monitoring Data Set"
    ::= { ieee1588Groups 29 }


ieee1588PerfMonPortDsGrp  OBJECT-GROUP
    OBJECTS {
        ieee1588PerfMonPortDsRecordListPmTime,
        ieee1588PerfMonPortDsRecordListAnnounceTx,
        ieee1588PerfMonPortDsRecordListAnnounceRx,
        ieee1588PerfMonPortDsRecordListAnnounceFMasterRx,
        ieee1588PerfMonPortDsRecordListSyncTx,
        ieee1588PerfMonPortDsRecordListSyncRx,
        ieee1588PerfMonPortDsRecordListFollowUpTx,
        ieee1588PerfMonPortDsRecordListFollowUpRx,
        ieee1588PerfMonPortDsRecordListDelayReqTx,
        ieee1588PerfMonPortDsRecordListDelayReqRx,
        ieee1588PerfMonPortDsRecordListDelayRespTx,
        ieee1588PerfMonPortDsRecordListDelayRespRx,
        ieee1588PerfMonPortDsRecordListPDelayReqTx,
        ieee1588PerfMonPortDsRecordListPDelayReqRx,
        ieee1588PerfMonPortDsRecordListPDelayRespTx,
        ieee1588PerfMonPortDsRecordListPDelayRespRx,
        ieee1588PerfMonPortDsRecordListPDelayRespFollowUpTx,
        ieee1588PerfMonPortDsRecordListPDelayRespFollowUpRx
        }
    STATUS       current
    DESCRIPTION
        "Objects in the Performance Monitoring Port Data Set"
    ::= { ieee1588Groups 30 }


ieee1588PerfMonPortDsPdGrp  OBJECT-GROUP
    OBJECTS {
        ieee1588PerfMonPortDsRecordListPdPmTime,
        ieee1588PerfMonPortDsRecordListPdAverMeanLinkDelay,
        ieee1588PerfMonPortDsRecordListPdMinMeanLinkDelay,
        ieee1588PerfMonPortDsRecordListPdMaxMeanLinkDelay,
        ieee1588PerfMonPortDsRecordListPdStdDevMLinkDelay
        }
    STATUS       current
    DESCRIPTION
        "Objects in the Performance Monitoring Port Peer Delay Data Set"
    ::= { ieee1588Groups 31 }


ieee1588CmldsPerfMonPortDsGrp  OBJECT-GROUP
    OBJECTS {
        ieee1588CmldsPerfMonPortDsRecordListPmTime,
        ieee1588CmldsPerfMonPortDsRecordListAnnounceTx,
        ieee1588CmldsPerfMonPortDsRecordListAnnounceRx,
        ieee1588CmldsPerfMonPortDsRecordListAnnounceFMasterRx,
        ieee1588CmldsPerfMonPortDsRecordListSyncTx,
        ieee1588CmldsPerfMonPortDsRecordListSyncRx,
        ieee1588CmldsPerfMonPortDsRecordListFollowUpTx,
        ieee1588CmldsPerfMonPortDsRecordListFollowUpRx,
        ieee1588CmldsPerfMonPortDsRecordListDelayReqTx,
        ieee1588CmldsPerfMonPortDsRecordListDelayReqRx,
        ieee1588CmldsPerfMonPortDsRecordListDelayRespTx,
        ieee1588CmldsPerfMonPortDsRecordListDelayRespRx,
        ieee1588CmldsPerfMonPortDsRecordListPDelayReqTx,
        ieee1588CmldsPerfMonPortDsRecordListPDelayReqRx,
        ieee1588CmldsPerfMonPortDsRecordListPDelayRespTx,
        ieee1588CmldsPerfMonPortDsRecordListPDelayRespRx,
        ieee1588CmldsPerfMonPortDsRecordListPDelayRespFollowUpTx,
        ieee1588CmldsPerfMonPortDsRecordListPDelayRespFollowUpRx
        }
    STATUS       current
    DESCRIPTION
        "Objects in the Common Mean Link Delay Service Performance
        Monitoring Port Data Set"
    ::= { ieee1588Groups 32 }


ieee1588CmldsPerfMonPortDsPdGrp  OBJECT-GROUP
    OBJECTS {
        ieee1588CmldsPerfMonPortDsRecordListPdPmTime,
        ieee1588CmldsPerfMonPortDsRecordListPdAverMeanLinkDelay,
        ieee1588CmldsPerfMonPortDsRecordListPdMinMeanLinkDelay,
        ieee1588CmldsPerfMonPortDsRecordListPdMaxMeanLinkDelay,
        ieee1588CmldsPerfMonPortDsRecordListPdStdDevMLinkDelay
        }
    STATUS       current
    DESCRIPTION
        "Objects in the Common Mean Link Delay Service Performance
        Monitoring Port Peer Delay Data Set"
    ::= { ieee1588Groups 33 }


ieee1588PortDsGrp  OBJECT-GROUP
    OBJECTS {
        ieee1588PortDsPortIdentityClockIdentity,
        ieee1588PortDsPortIdentityPortNumber,
        ieee1588PortDsPortState,
        ieee1588PortDsLogMinDelayReqInterval,
        ieee1588PortDsMeanLinkDelay,
        ieee1588PortDsLogAnnounceInterval,
        ieee1588PortDsAnnounceReceiptTimeout,
        ieee1588PortDsLogSyncInterval,
        ieee1588PortDsDelayMechanism,
        ieee1588PortDsLogMinPdelayReqInterval,
        ieee1588PortDsVersionNumber,
        ieee1588PortDsMinorVersionNumber,
        ieee1588PortDsDelayAsymmetry,
        ieee1588PortDsPortEnable,
        ieee1588PortDsMasterOnly
        }
    STATUS       current
    DESCRIPTION
        "Objects in the Port Data Set"
    ::= { ieee1588Groups 34 }


ieee1588SlaveMonitoringPortDsGrp  OBJECT-GROUP
    OBJECTS {
        ieee1588SlaveMonitoringPortDsSlaveEventMonEnable,
        ieee1588SlaveMonitoringPortDsSlaveEventMonEventsPerRxSyncTimTLV,
        ieee1588SlaveMonitoringPortDsSlaveEventMonEventsPerRxSyncCompTLV,
        ieee1588SlaveMonitoringPortDsSlaveEventMonEventsPerTxEventTsTLV,
        ieee1588SlaveMonitoringPortDsSlaveEventMonTxEventType,
        ieee1588SlaveMonitoringPortDsSlaveEventMonRxSyncTimEventMsgM,
        ieee1588SlaveMonitoringPortDsSlaveEventMonRxSyncCompEventMsgM,
        ieee1588SlaveMonitoringPortDsSlaveEventMonTxEventTsEventMsgM
        }
    STATUS       current
    DESCRIPTION
        "Objects in the Slave Monitoring Port Data Set"
    ::= { ieee1588Groups 35 }


ieee1588TcDefaultDsGrp  OBJECT-GROUP
    OBJECTS {
        ieee1588TcDefaultDsClockIdentity,
        ieee1588TcDefaultDsNumberPorts,
        ieee1588TcDefaultDsDelayMechanism,
        ieee1588TcDefaultDsPrimaryDomain
        }
    STATUS       deprecated
    DESCRIPTION
        "Objects in the Transparent Clock Default Data Set"
    ::= { ieee1588Groups 36 }


ieee1588TcPortDsGrp  OBJECT-GROUP
    OBJECTS {
        ieee1588TcPortDsLocalPortIfIndex,
        ieee1588TcPortDsPortIdentityClockIdentity,
        ieee1588TcPortDsPortIdentityPortNumber,
        ieee1588TcPortDsLogMinPdelayReqInterv,
        ieee1588TcPortDsFaultyFlag,
        ieee1588TcPortDsPeerMeanPathDelay
        }
    STATUS       deprecated
    DESCRIPTION
        "Objects in the Transparent Clock Port Data Set"
    ::= { ieee1588Groups 37 }


ieee1588TimePropertiesDsGrp  OBJECT-GROUP
    OBJECTS {
        ieee1588TimePropertiesDsCurrentUtcOffset,
        ieee1588TimePropertiesDsCurrentUtcOffsetValid,
        ieee1588TimePropertiesDsLeap59,
        ieee1588TimePropertiesDsLeap61,
        ieee1588TimePropertiesDsTimeTraceable,
        ieee1588TimePropertiesDsFrequencyTraceable,
        ieee1588TimePropertiesDsPtpTimescale,
        ieee1588TimePropertiesDsTimeSource
        }
    STATUS       current
    DESCRIPTION
        "Objects in the Time Properties Data Set"
    ::= { ieee1588Groups 38 }


ieee1588TimestampCorrectionPortDsGrp  OBJECT-GROUP
    OBJECTS {
        ieee1588TimestampCorrectionPortDsEgressLatency,
        ieee1588TimestampCorrectionPortDsIngressLatency
        }
    STATUS       current
    DESCRIPTION
        "Objects in the Timestamp Correction Port Data Set"
    ::= { ieee1588Groups 39 }


ieee1588UnicastDiscoveryPortDsGrp  OBJECT-GROUP
    OBJECTS {
        ieee1588UnicastDiscoveryPortDsMaxTableSize,
        ieee1588UnicastDiscoveryPortDsLogQueryInterval,
        ieee1588UnicastDiscoveryPortDsPortRowStatus,
        ieee1588UnicastDiscoveryPortDsPortAddressNetworkProtocol,
        ieee1588UnicastDiscoveryPortDsPortAddressAddressLength,
        ieee1588UnicastDiscoveryPortDsPortAddressAddressField
        }
    STATUS       current
    DESCRIPTION
        "Objects in the Unicast Discovery Port Data Set"
    ::= { ieee1588Groups 40 }


ieee1588UnicastNegotiationPortDsGrp  OBJECT-GROUP
    OBJECTS {
        ieee1588UnicastNegotiationPortDsEnable
        }
    STATUS       current
    DESCRIPTION
        "Objects in the Unicast Negotiation Port Data Set"
    ::= { ieee1588Groups 41 }



--=====================================================================
-- MIB module Compliance statements
--=====================================================================

ieee1588Compliances OBJECT IDENTIFIER ::= { ieee1588Conformance 2 }
ieee1588Compliance MODULE-COMPLIANCE
    STATUS current
    DESCRIPTION
        "The compliance statement for IEEE1588-MS-MIB groups"
    MODULE
        GROUP ieee1588AcceptableMasterPortDsGrp
        DESCRIPTION
            "This group is optional."

        GROUP ieee1588AcceptableMasterTableDsGrp
        DESCRIPTION
            "This group is optional."

        GROUP ieee1588AlternateMasterPortDsGrp
        DESCRIPTION
            "This group is optional."

        GROUP ieee1588AlternateTimeScaleOffsetDsGrp
        DESCRIPTION
            "This group is optional."

        GROUP ieee1588AsymmetryCorrectionPortDsGrp
        DESCRIPTION
            "This group is optional."

        GROUP ieee1588BaseInstanceGrp
        DESCRIPTION
            "This group is optional."

        GROUP ieee1588BasePortGrp
        DESCRIPTION
            "This group is optional."

        GROUP ieee1588CmldsAsymmetryCorrectionLinkPortDsGrp
        DESCRIPTION
            "This group is optional."

        GROUP ieee1588CmldsLinkPortDsGrp
        DESCRIPTION
            "This group is optional."

        GROUP ieee1588CmldsTimestampCorrectionLinkPortDsGrp
        DESCRIPTION
            "This group is optional."

        GROUP ieee1588CommonServicesPortDsGrp
        DESCRIPTION
            "This group is optional."

        GROUP ieee1588CommunicationCapabilitiesPortDsGrp
        DESCRIPTION
            "This group is optional."

        GROUP ieee1588CurrentDsGrp
        DESCRIPTION
            "This group is optional."

        GROUP ieee1588DefaultDsGrp
        DESCRIPTION
            "This group is optional."

        GROUP ieee1588DescriptionDsGrp
        DESCRIPTION
            "This group is optional."

        GROUP ieee1588DescriptionPortDsGrp
        DESCRIPTION
            "This group is optional."

        GROUP ieee1588EnhancedSynchronizationAccuracyMetricsDsGrp
        DESCRIPTION
            "This group is optional."

        GROUP ieee1588ExternalPortConfigurationPortDsGrp
        DESCRIPTION
            "This group is optional."

        GROUP ieee1588FaultLogDsGrp
        DESCRIPTION
            "This group is optional."

        GROUP ieee1588GrandmasterClusterDsGrp
        DESCRIPTION
            "This group is optional."

        GROUP ieee1588HoldoverUpgradeDsGrp
        DESCRIPTION
            "This group is optional."

        GROUP ieee1588L1SyncBasicPortDsGrp
        DESCRIPTION
            "This group is optional."

        GROUP ieee1588L1SyncOptParamsPortDsGrp
        DESCRIPTION
            "This group is optional."

        GROUP ieee1588NonVolatileStorageDsGrp
        DESCRIPTION
            "This group is optional."

        GROUP ieee1588ParentDsGrp
        DESCRIPTION
            "This group is optional."

        GROUP ieee1588PathTraceDsGrp
        DESCRIPTION
            "This group is optional."

        GROUP ieee1588PerfMonDsGrp
        DESCRIPTION
            "This group is optional."

        GROUP ieee1588PerfMonPortDsGrp
        DESCRIPTION
            "This group is optional."

        GROUP ieee1588PerfMonPortDsPdGrp
        DESCRIPTION
            "This group is optional."

        GROUP ieee1588CmldsPerfMonPortDsGrp
        DESCRIPTION
            "This group is optional."

        GROUP ieee1588CmldsPerfMonPortDsPdGrp
        DESCRIPTION
            "This group is optional."

        GROUP ieee1588PortDsGrp
        DESCRIPTION
            "This group is optional."

        GROUP ieee1588SlaveMonitoringPortDsGrp
        DESCRIPTION
            "This group is optional."

        GROUP ieee1588TimePropertiesDsGrp
        DESCRIPTION
            "This group is optional."

        GROUP ieee1588TimestampCorrectionPortDsGrp
        DESCRIPTION
            "This group is optional."

        GROUP ieee1588UnicastDiscoveryPortDsGrp
        DESCRIPTION
            "This group is optional."

        GROUP ieee1588UnicastNegotiationPortDsGrp
        DESCRIPTION
            "This group is optional."

        ::= { ieee1588Compliances 1 }

ieee1588ComplianceDeprecated MODULE-COMPLIANCE
    STATUS deprecated
    DESCRIPTION
        "The compliance statement for deprecated IEEE1588-MS-MIB groups"
    MODULE
        GROUP ieee1588CmldsDefaultDsGrp
        DESCRIPTION
            "This group is optional."

        GROUP ieee1588DefaultDsDeprecatedGrp
        DESCRIPTION
            "This group is optional."

        GROUP ieee1588TcDefaultDsGrp
        DESCRIPTION
            "This group is optional."

        GROUP ieee1588TcPortDsGrp
        DESCRIPTION
            "This group is optional."

        ::= { ieee1588Compliances 2 }

END
