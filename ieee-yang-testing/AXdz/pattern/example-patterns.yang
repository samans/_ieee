module example-patterns {
    namespace "urn:example:patterns";
    prefix "ep";

    container example-container {
       list patterns {
          key "name";
            
          leaf name {
             type string;
                description "Name of test";
          }
          leaf my-number-pattern-mod {
             type string {
                pattern '([0-9]{1}|[1-9]{1}[0-9]{1,2}|[1-3]{1}[0-9]{3}|40[0-8]{1}[0-9]{1}|409[0-5]{1})' +
                        '(-([1-9]{1}[0-9]{0,2}|[1-3][0-9]{3}|40[0-8]{1}[0-9]{1}|409[0-5]{1}))?' +
                        '(,([1-9]{1}|[1-9]{1}[0-9]{1,2}|[1-3]{1}[0-9]{3}|40[0-8]{1}[0-9]{1}|409[0-5]{1})' +
                          '(-([1-9]{1}[0-9]{0,2}|[1-3][0-9]{3}|40{1}[0-8]{1}[0-9]{1}|409[0-5]{1}))?)*';
             }
             description "A leaf that accepts comma-separated individual values and ranges like 1,5,6-10,2000-3000,4094.";
          }
          leaf my-number-pattern-odd-even {
             type string {
                pattern '((([0-9]{1}|[1-9]{1}[0-9]{1,2}|[1-3]{1}[0-9]{3}|40[0-8]{1}[0-9]{1}|409[0-5]{1})' +
                        '(-([1-9]{1}[0-9]{0,2}|[1-3][0-9]{3}|40[0-8]{1}[0-9]{1}|409[0-5]{1}))?)' +
                        '|(even\(([0-9]{1}|[1-9]{1}[0-9]{1,2}|[1-3]{1}[0-9]{3}|40[0-8]{1}[0-9]{1}|409[0-5]{1})' +
                           '(-([1-9]{1}[0-9]{0,2}|[1-3][0-9]{3}|40[0-8]{1}[0-9]{1}|409[0-5]{1}))?\))' +
                        '|(odd\(([0-9]{1}|[1-9]{1}[0-9]{1,2}|[1-3]{1}[0-9]{3}|40[0-8]{1}[0-9]{1}|409[0-5]{1})' +
                           '(-([1-9]{1}[0-9]{0,2}|[1-3][0-9]{3}|40[0-8]{1}[0-9]{1}|409[0-5]{1}))?\)))' +
                        '(,((([1-9]{1}|[1-9]{1}[0-9]{1,2}|[1-3]{1}[0-9]{3}|40[0-8]{1}[0-9]{1}|409[0-5]{1})' +
                          '(-([1-9]{1}[0-9]{0,2}|[1-3][0-9]{3}|40{1}[0-8]{1}[0-9]{1}|409[0-5]{1}))?)' +
                        '|(even\(([1-9]{1}|[1-9]{1}[0-9]{1,2}|[1-3]{1}[0-9]{3}|40[0-8]{1}[0-9]{1}|409[0-5]{1})' +
                          '(-([1-9]{1}[0-9]{0,2}|[1-3][0-9]{3}|40{1}[0-8]{1}[0-9]{1}|409[0-5]{1}))?\))' +
                        '|(odd\(([1-9]{1}|[1-9]{1}[0-9]{1,2}|[1-3]{1}[0-9]{3}|40[0-8]{1}[0-9]{1}|409[0-5]{1})' +
                          '(-([1-9]{1}[0-9]{0,2}|[1-3][0-9]{3}|40{1}[0-8]{1}[0-9]{1}|409[0-5]{1}))?\))))*';
             }
             description "A leaf that accepts comma-separated individual values and ranges" +
                         "like 1,5,6-10,2000-3000,4094. And supports limiting to odd or even numbers in the pattern";
          }

          leaf my-number-pattern-odd-even-extended {
             type string {
                pattern '(([0-9]{1}|[1-9]{1}[0-9]{1,2}|[1-3]{1}[0-9]{3}|40[0-8]{1}[0-9]{1}|409[0-5]{1}(-[0-9]{1}|[1-9]{1}[0-9]{1,2}|[1-3]{1}[0-9]{3}|40[0-8]{1}[0-9]{1}|409[0-5]{1})?)' +
                  '|(even\([0-9]{1}|[1-9]{1}[0-9]{1,2}|[1-3]{1}[0-9]{3}|40[0-8]{1}[0-9]{1}|409[0-5]{1}(-[0-9]{1}|[1-9]{1}[0-9]{1,2}|[1-3]{1}[0-9]{3}|40[0-8]{1}[0-9]{1}|409[0-5]{1})?(,([0-9]{1}|[1-9]{1}[0-9]{1,2}|[1-3]{1}[0-9]{3}|40[0-8]{1}[0-9]{1}|409[0-5]{1}(-[0-9]{1}|[1-9]{1}[0-9]{1,2}|[1-3]{1}[0-9]{3}|40[0-8]{1}[0-9]{1}|409[0-5]{1})?))*\))' +
                  '|(odd\([0-9]{1}|[1-9]{1}[0-9]{1,2}|[1-3]{1}[0-9]{3}|40[0-8]{1}[0-9]{1}|409[0-5]{1}(-[0-9]{1}|[1-9]{1}[0-9]{1,2}|[1-3]{1}[0-9]{3}|40[0-8]{1}[0-9]{1}|409[0-5]{1})?(,([0-9]{1}|[1-9]{1}[0-9]{1,2}|[1-3]{1}[0-9]{3}|40[0-8]{1}[0-9]{1}|409[0-5]{1}(-[0-9]{1}|[1-9]{1}[0-9]{1,2}|[1-3]{1}[0-9]{3}|40[0-8]{1}[0-9]{1}|409[0-5]{1})?))*\)))' +
               '(,([0-9]{1}|[1-9]{1}[0-9]{1,2}|[1-3]{1}[0-9]{3}|40[0-8]{1}[0-9]{1}|409[0-5]{1}(-[0-9]{1}|[1-9]{1}[0-9]{1,2}|[1-3]{1}[0-9]{3}|40[0-8]{1}[0-9]{1}|409[0-5]{1})?)' +
                  '|(even\([0-9]{1}|[1-9]{1}[0-9]{1,2}|[1-3]{1}[0-9]{3}|40[0-8]{1}[0-9]{1}|409[0-5]{1}(-[0-9]{1}|[1-9]{1}[0-9]{1,2}|[1-3]{1}[0-9]{3}|40[0-8]{1}[0-9]{1}|409[0-5]{1})?(,([0-9]{1}|[1-9]{1}[0-9]{1,2}|[1-3]{1}[0-9]{3}|40[0-8]{1}[0-9]{1}|409[0-5]{1}(-[0-9]{1}|[1-9]{1}[0-9]{1,2}|[1-3]{1}[0-9]{3}|40[0-8]{1}[0-9]{1}|409[0-5]{1})?))*\))' +  
                  '|(odd\([0-9]{1}|[1-9]{1}[0-9]{1,2}|[1-3]{1}[0-9]{3}|40[0-8]{1}[0-9]{1}|409[0-5]{1}(-[0-9]{1}|[1-9]{1}[0-9]{1,2}|[1-3]{1}[0-9]{3}|40[0-8]{1}[0-9]{1}|409[0-5]{1})?(,([0-9]{1}|[1-9]{1}[0-9]{1,2}|[1-3]{1}[0-9]{3}|40[0-8]{1}[0-9]{1}|409[0-5]{1}(-[0-9]{1}|[1-9]{1}[0-9]{1,2}|[1-3]{1}[0-9]{3}|40[0-8]{1}[0-9]{1}|409[0-5]{1})?))*\)))*';
             }
             description "A leaf that accepts comma-separated individual values and ranges" +
                         "like 1,5,6-10,2000-3000,4094. And supports limiting to odd or even numbers in the pattern";
          }
       }
   }
}
