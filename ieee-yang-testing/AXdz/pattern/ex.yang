module example-module {
    namespace "urn:example:module";
    prefix "ex";

    container example-container {
       list patterns {
          key "name";
            
          leaf name {
             type string;
                description "name of test pattern";
          }
          leaf my-number-pattern {
             type string {
                pattern '(0|[1-9][0-9]{0,3}|409[0-5])(-([1-9][0-9]{0,3}|409[0-5]))?(,(0|[1-9][0-9]{0,3}|409[0-5])(-([1-9][0-9]{0,3}|409[0-5]))?)*';
             }
             description "A leaf that accepts comma-separated individual values and ranges like 1,5,6-10,2000-3000,4094.";
          }
          leaf my-number-pattern-mod {
             type string {
                pattern '([0-9]{1}|[1-9]{1}[0-9]{1,2}|[1-3]{1}[0-9]{3}|40[0-9]{1}[0-5]{1})(-([1-9]{1}[0-9]{0,2}|[1-3][0-9]{3}|4{1}[0-9]{2}[0-5]{1}))?(,([1-9]{1}|[1-9]{1}[0-9]{1,2}|[1-3]{1}[0-9]{3}|40[0-9]{1}[0-5]{1})(-([1-9]{1}[0-9]{0,2}|[1-3][0-9]{3}|4{1}[0-9]{2}[0-5]{1}))?)*';
             }
             description "A leaf that accepts comma-separated individual values and ranges like 1,5,6-10,2000-3000,4094.";
          }
          leaf my-number-pattern-part1 {
             type string {
                pattern '(0|[1-9][0-9]{0,3}|409[0-5])';
             }
             description "part 1";
          }
          leaf my-number-pattern-part1-mod-01 {
             type string {
                pattern '(0|[1-9][0-9]{0,3}|409[0-5])';
             }
             description "part 1";
          }
          leaf my-number-pattern-part1-mod-02 {
             type string {
                pattern '(0|[1-3][0-9]{0,3}|4{1}[0-9]{2}[0-5]{1})';
             }
             description "part 1";
          }
          leaf my-number-pattern-part1-mod-03 {
             type string {
                pattern '([0-9]{1}|[1-9]{1}[0-9]{1,2}|[1-3][0-9]{3}|4{1}[0-9]{2}[0-5]{1})';
             }
             description "part 1";
          }
       }
   }
}
