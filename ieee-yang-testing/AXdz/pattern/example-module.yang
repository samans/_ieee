module example-module {
    namespace "urn:example:module";
    prefix "ex";

    container example-container {
       list range-tests {
          key "name";

          leaf name {
             type string;
                description "Name of test";
          }

          list ranges {
             key "range-element-name";

             leaf range-element-name {
                type string;
                   description "Range Element Name";
             }
             leaf lower {
                type int16;
                   description "lower bound of range element";
             }    
             leaf upper {
                type int16;
                   description "upper bound of range element";
             }    
          }
       }
       list patterns {
          key "name";
            
          leaf name {
             type string;
                description "Name of test";
          }
          leaf my-number-pattern {
             type string {
                pattern '(0|[1-9][0-9]{0,3}|409[0-5])(-([1-9][0-9]{0,3}|409[0-5]))?(,(0|[1-9][0-9]{0,3}|409[0-5])(-([1-9][0-9]{0,3}|409[0-5]))?)*';
             }
             description "A leaf that accepts comma-separated individual values and ranges like 1,5,6-10,2000-3000,4094.";
          }
          leaf my-number-pattern-mod {
             type string {
                pattern '([0-9]{1}|[1-9]{1}[0-9]{1,2}|[1-3]{1}[0-9]{3}|40[0-8]{1}[0-9]{1}|409[0-5]{1})(-([1-9]{1}[0-9]{0,2}|[1-3][0-9]{3}|40[0-8]{1}[0-9]{1}|409[0-5]{1}))?(,([1-9]{1}|[1-9]{1}[0-9]{1,2}|[1-3]{1}[0-9]{3}|40[0-8]{1}[0-9]{1}|409[0-5]{1})(-([1-9]{1}[0-9]{0,2}|[1-3][0-9]{3}|40{1}[0-8]{1}[0-9]{1}|409[0-5]{1}))?)*';
             }
             description "A leaf that accepts comma-separated individual values and ranges like 1,5,6-10,2000-3000,4094.";
          }
       }
   }
}
