module ieee802-dot1ax-types {
  yang-version 1.1;
  namespace "urn:ieee:params:xml:ns:yang:ieee802-dot1ax-types";
  prefix "dot1ax-types";

  import iana-if-type {
    prefix "ianaif";
  }

  organization
    "Institute of Electrical and Electronics Engineers";

  contact
      "Web URL: http://www.ieee802.org/1/

       Working Group Chair:
        Glenn Parsons
        glenn.parsons@ericsson.com

       Editor:
         Stephen Haddock
         shaddock@stanfordalumni.org";

  description
    "Common types used within 802.1AX Link Aggregation modules.
    
    Copyright (C) IEEE (2024).
    
    This version of this YANG module is part of IEEE Std 802.1AX;
    see the standard itself for full legal notices.";


  revision "2024-05-04" {
    description
      "Initial Version.";
    reference
      "IEEE 802.1AX-2020, Link Aggregation.";
  }


  feature cscd {
    description
      "Conversation Sensitive Collection and Distribution (CSCD) 
      is supported.";
    reference
      "IEEE 802.1AX-2020, Clause 5.3.2, Clause 6.6";
  }

  feature dwc {
    description
      "The Discard Wrong Conversation option in CSCD is 
      supported.";
    reference
      "IEEE 802.1AX-2020, Clause 5.3.2, Clause 6.6";
  }

  typedef lacp-state {
    type bits {
      bit lacp-activity {
        position 0;
        description
          "Provides administrative control over when LACPDUs are 
          transmitted.  A value of '1' indicates Active mode where
          LACPDUs are sent regardless of partner's lacp-activity 
          value.  A value of '0' indicates Passive mode where 
          LACPDUs are sent only when the partner's lacp-activity 
          value is '1' (partner is in Active mode).";
      }
      bit lacp-timeout {
        position 1;
        description
          "Provides administrative control over the frequency of 
          received LACPDUs.  A value of '1' indicates Short Timeout
          (so partner uses frequent transmission).  A value of '0' 
          indicates Long Timeout (so partner can use infrequent 
          transmission).";
      }
      bit aggregation {
        position 2;
        description
          "Provides administrative control over whether this 
          Aggregation Port can be in a LAG with more than one 
          member.  A value of '1' indicates the port can be 
          aggregated with other ports.  A value of '0' indicates 
          the port can only be a solitary link.";
      }
      bit synchronization {
        position 3;
        description
          "The Synchronization state of the MUX state machine.";
      }
      bit collecting {
        position 4;
        description
          "The Collecting state of the MUX state machine.";
      }
      bit distributing {
        position 5;
        description
          "The Distributing state of the MUX state machine.";
      }
      bit defaulted {
        position 6;
        description
          "Indicates the port is using the partner-admin values 
          to select an Aggregator.";
      }
      bit expired {
        position 7;
        description
          "The Expired state of the Receive state machine.";
      }
    }
    description
      "LACP state values as transmitted in LACPDUs.";
    reference
      "IEEE 802.1AX-2020, Clause 6.4.1, Clause 6.4.2.3";
  }

  typedef irp-state {
    type bits {
      bit reserved-1 {
        position 0;
        description
          "Reserved for future use. It is set to 0 on
           transmit and ignored on receipt.";
      }
      bit reserved-2 {
        position 1;
        description
          "Reserved for future use. It is set to 0 on
           transmit and ignored on receipt.";
      }
      bit short-timeout {
        position 2;
        description
          "The Short_Timeout flag indicates the Timeout control value 
           in use by the DRCP Receive machine on this IRP. Short Timeout
           is encoded as a 1; Long Timeout is encoded as a 0.";
      }
      bit synchronization {
        position 3;
        description
          "When the Sync flag is TRUE (1), the DRCP Receive machine has 
           determined the Neighbor DRNI System has a compatible
           configuration for forming a DRNI.";
      }
      bit irc-data {
        position 4;
        description
          "When the IRC_Data flag is TRUE (1), the transfer of Up 
           and Down frames is permitted on the IRC.";
      }
      bit drni {
        position 5;
        description
          "The DRNI flag is TRUE (1) when this DRNI System is paired 
           with another DRNI System (i.e., when DR_Solo is FALSE) 
           and FALSE (0) otherwise.";
      }
      bit defaulted {
        position 6;
        description
          "When the Defaulted flag is TRUE (1), the DRCP Receive machine 
           is using default operational Neighbor information. 
           When FALSE (0), the operational Neighbor information 
           in use has been received in a DRCPDU.";
      }
      bit expired {
        position 7;
        description
          "When the Expired flag is TRUE (1), the DRCP Receive machine 
           is in the EXPIRED state.";
      }
    }
    description
      "A string of 8 bits, corresponding to the administrative
       values of IRP_State (9.6.2.3 and Figure 9-13). 
       These values allow administrative control over the  
       values of Short_Timeout and IRC_Data.
       
       Implementers are recommended to review Figure 9-13 for
       a diagram of the bit-values. Take note of the 0-7
       aligned YANG bits compared to the 1-8 aligned bits from
       the IEEE specification. Also note that while some of
       these elements are operational by design / by default,
       having an admin value allows for manual override config.";
    reference
      "IEEE 802.1AX-2020, Clause 7.4.1.1.24, 9.6.2.3, Figure 9-13";
  }


  identity distribution-algorithm {
    description
      "Each distribution algorithm is identified by a sequence of 
       4octets, structured as shown in Figure 8-1. Distribution
       algorithm identifiers are used by network administrators to
       select between algorithms and, in Conversation-sensitive 
       LACP and Distributed Resilient Network Interconnect (DRNI) 
       operation, to check whether partners and neighbors are 
       using the same algorithm.
       
       This identity is intended to serve as base identity, not 
       to be directly referenced.
       
       Vendor specific, combination (ex: multi-layer), and other
       customized distribution algorithms should be created as 
       their own identities in their own YANG files, derived from  
       this imported base type.";
     reference
       "IEEE 802.1AX-2020, Clause 8.1, Clause 8.2";
  }
  identity unspecified {
    base distribution-algorithm;
    description
      "The 'Unspecified distribution algorithm' identifier has been
       reserved for use when the algorithm is unknown (or is not
       advertised).";
    reference
      "IEEE 802.1AX-2020, Table 8-1";
  }
  identity c-vids-nomap {
    base distribution-algorithm;
    description
      "Distribution based on C-VIDs (8.2.1). No Service ID mapping
       table is used.";
    reference
      "IEEE 802.1AX-2020, Table 8-1";
  }
  identity c-vids-map {
    base distribution-algorithm;
    description
      "Distribution based on C-VIDs (8.2.1). A Service ID mapping table
       is used.";
    reference
      "IEEE 802.1AX-2020, Table 8-1";
  }
  identity s-vids-nomap {
    base distribution-algorithm;
    description
      "Distribution based on S-VIDs (8.2.2). No Service ID mapping
       table is used.";
    reference
      "IEEE 802.1AX-2020, Table 8-1";
  }
  identity s-vids-map {
    base distribution-algorithm;
    description
      "Distribution based on S-VIDs (8.2.2). A Service ID mapping table
       is used.";
    reference
      "IEEE 802.1AX-2020, Table 8-1";
  }
  identity i-sids-nomap {
    base distribution-algorithm;
    description
      "Distribution based on I-SIDs (8.2.3). No Service ID mapping
       table is used.";
    reference
      "IEEE 802.1AX-2020, Table 8-1";
  }
  identity i-sids-map {
    base distribution-algorithm;
    description
      "Distribution based on I-SIDs (8.2.3). A Service ID mapping table
       is used.";
    reference
      "IEEE 802.1AX-2020, Table 8-1";
  }
  identity te-sids-nomap {
    base distribution-algorithm;
    description
      "Distribution based on TE-SIDs (8.2.4). No Service ID mapping
       table is used.";
    reference
      "IEEE 802.1AX-2020, Table 8-1";
  }
  identity te-sids-map {
    base distribution-algorithm;
    description
      "Distribution based on TE-SIDs (8.2.4). A Service ID mapping table
       is used.";
    reference
      "IEEE 802.1AX-2020, Table 8-1";
  }
  identity flow-hash-nomap {
    base distribution-algorithm;
    description
      "Distribution based on Flow Hash (8.2.5). No Service ID mapping
       table is used.";
    reference
      "IEEE 802.1AX-2020, Table 8-1";
  }
  identity flow-hash-map {
    base distribution-algorithm;
    description
      "Distribution based on Flow Hash (8.2.5). A Service ID mapping table
       is used.";
    reference
      "IEEE 802.1AX-2020, Table 8-1";
  }


  identity ieee8021axIrp {
    base ianaif:iana-interface-type;
    description
      "IEEE 802.1ax Intra-Relay Port.";
  }

}
