IEEE8021-PBBN-AA-MIB DEFINITIONS ::= BEGIN

-- =============================================================
-- MIB for support of PBBN auto attach to Provider Backbone 
-- Bridging (PBB) services.
-- =============================================================

IMPORTS
    MODULE-IDENTITY, OBJECT-TYPE, Integer32, Gauge32, Unsigned32, Counter32,
    NOTIFICATION-TYPE
        FROM SNMPv2-SMI
    SnmpAdminString
            FROM SNMP-FRAMEWORK-MIB
    RowStatus, TruthValue, MacAddress
            FROM SNMPv2-TC
    MODULE-COMPLIANCE, OBJECT-GROUP, NOTIFICATION-GROUP
            FROM SNMPv2-CONF;

ieee8021PbbnAutoAttachMib MODULE-IDENTITY
    LAST-UPDATED "202209260000Z"     -- September 26, 2022
    ORGANIZATION "IEEE 802.1 Working Group"
    CONTACT-INFO	
        "  WG-URL: http://www.ieee802.org/1/
         WG-EMail: stds-802-1-l@ieee.org
          Contact: IEEE 802.1 Working Group Chair
           Postal: C/O IEEE 802.1 Working Group
                   IEEE Standards Association
                   445 Hoes Lane
                   Piscataway, NJ 08854
                   USA
           E-mail: stds-802-1-chairs@ieee.org"
    DESCRIPTION
        "This Management Information Base module contains objects related to the
		configuration and statistics for PBBN auto attach support."
		
    REVISION    "202209260000Z" -- September 26, 2022
     DESCRIPTION
        "Updated IEEE 802.1Qcj MIB based on ballot comments on
		draft D1.4 and D1.5 reviewed at the September 2022 interim. The naming prefix 
		has been changed to ieee8021Aa. The SystemID has been renamed portNetId. 
		The authentication objects have been removed. The expired discovered system
		table has been removed. New objects for	the systemMAC, local portNetId, 
		DiscSystemsRemAssocState, and DiscSystemsLocAssocState have been added. The 
		statistics counter clearing functions StatsClearErrorCounters and
		StatsClearPortErrorCounters have been removed and the statistics
		StatsAssocAttempts and StatsAssocErrors have been replaced by the new
		statistics StatsAssocAttached, StatsAssocFailed, StatsAssocStandby, and
		StatsAssocReset. The SystemType now is extended to include S-VLAN aware AADs.
		The DiscRemPortAssocState and DiscLocPortAssocState are now updated with
		with new state names.
		
		
    REVISION    "202106020000Z" -- June 2, 2021
     DESCRIPTION
        "Published as part of IEEE 802.1Qcj initial draft."
		
   ::= { iso std(0) iso8802(8802) ieee802dot1(1) ieee802dot1mibs(1) xx }

ieee8021AaNotifications OBJECT IDENTIFIER ::= { ieee8021PbbnAutoAttachMib 0 }
ieee8021AaObjects       OBJECT IDENTIFIER ::= { ieee8021PbbnAutoAttachMib 1 }
ieee8021AaNotifyObjects OBJECT IDENTIFIER ::= { ieee8021PbbnAutoAttachMib 2 }

ieee8021AaConfig  	OBJECT IDENTIFIER ::= { ieee8021AaObjects 1 }
ieee8021AaStats  	OBJECT IDENTIFIER ::= { ieee8021AaObjects 2 }

-- ===============================================================
-- Auto attach scalar attributes
-- ===============================================================

ieee8021AaSystemEnable OBJECT-TYPE
    SYNTAX         INTEGER {
                       enabled(1),
                       disabled(2)
                   }
    MAX-ACCESS     read-write
    STATUS         current
    DESCRIPTION
        "Exports the status of the auto attach service on this system."
    ::= { ieee8021AaConfig 1 }

ieee8021AaSystemType OBJECT-TYPE
    SYNTAX         INTEGER {
                       aaBeb(1),
                       aaDeviceVlanAware(2),
                       aaDeviceVlanUnaware(3)
                   }
    MAX-ACCESS     read-only
    STATUS         current
    DESCRIPTION
        "Defines the AAS type indicating the services supported by the
		system. May be read-only on platforms that only support a single system type."
    ::= { ieee8021AaConfig 2 }
	
ieee8021AaSystemMac OBJECT-TYPE
    SYNTAX         MacAddress
    MAX-ACCESS     read-only
    STATUS         current
    DESCRIPTION
        "Defines the auto attach system MAC used to uniquely identify this system."
    ::= { ieee8021AaConfig 3 }
	
ieee8021AaSystemResetTime OBJECT-TYPE
    SYNTAX         Integer32 (1..1200)
    MAX-ACCESS     read-write
    STATUS         current
    DESCRIPTION
        "AAP reset time delay used to re-synchronize the associated AASs"
    ::= { ieee8021AaConfig 4 }

-- ===============================================================
-- Auto attach VID/I-SID assignment table support        
-- ===============================================================

ieee8021AaVidIsidAsgnsTable OBJECT-TYPE
    SYNTAX      SEQUENCE OF Ieee8021AaVidIsidAsgnsEntry
    MAX-ACCESS  not-accessible
    STATUS      current
    DESCRIPTION
        "This table contains the VID <-> I-SID assignments for the auto attach application."
    ::= { ieee8021AaConfig 4 }

ieee8021AaVidIsidAsgnsEntry OBJECT-TYPE
    SYNTAX      Ieee8021AaVidIsidAsgnsEntry
    MAX-ACCESS  not-accessible
    STATUS      current
    DESCRIPTION
        "Information about the I-SID <-> VID assignments for the auto attach application."
    INDEX { ieee8021AaVidIsidAsgnsIfIndex, 
            ieee8021AaVidIsidAsgnsIsid, 
            ieee8021AaVidIsidAsgnsVid }
    ::= { ieee8021AaVidIsidAsgnsTable 1 }

Ieee8021AaVidIsidAsgnsEntry ::= SEQUENCE {
    ieee8021AaVidIsidAsgnsIfIndex    Integer32,
    ieee8021AaVidIsidAsgnsIsid       Integer32,
    ieee8021AaVidIsidAsgnsVid       Integer32,
    ieee8021AaVidIsidAsgnsStatus     INTEGER,
    ieee8021AaVidIsidAsgnsRowStatus  RowStatus }

ieee8021AaVidIsidAsgnsIfIndex OBJECT-TYPE
    SYNTAX         Integer32 (0..65535)
    MAX-ACCESS     not-accessible
    STATUS         current
    DESCRIPTION
        "Interface identifier component of the I-SID <-> VID assignment."
    ::= { ieee8021AaVidIsidAsgnsEntry 1 }

ieee8021AaVidIsidAsgnsIsid OBJECT-TYPE
    SYNTAX         Integer32 (1,256..16777214)
    MAX-ACCESS     not-accessible
    STATUS         current
    DESCRIPTION
        "I-SID component of the I-SID <-> VID assignment."
    ::= { ieee8021AaVidIsidAsgnsEntry 2 }

ieee8021AaVidIsidAsgnsVid OBJECT-TYPE
    SYNTAX         Integer32 (1..4094)
    MAX-ACCESS     not-accessible
    STATUS         current
    DESCRIPTION
        "VLAN ID component of the I-SID <-> VID assignment."
    ::= { ieee8021AaVidIsidAsgnsEntry 3 }

ieee8021AaVidIsidAsgnsStatus OBJECT-TYPE
    SYNTAX         INTEGER {
                       pending(1),
					   accepted(2),
                       rejected(3),
                       rejectedAutoAttachResourcesUnavailable(4),
                       rejectedInvalidVLANID(5),
                       rejectedVLANResourcesUnavailable(6),
                       rejectedInvalidISID(7),
                       rejectedISIDResourcesUnavailable(8),
                       rejectedApplicationInteractionIssue(9),
                       rejectedAssignmentNotAllowed(10)
                   }
    MAX-ACCESS     read-only
    STATUS         current
    DESCRIPTION  
        "The current state of the auto attach I-SID <-> VID assignment.  Rejections can be from multiple causes including resources unavailable, duplicate, application interaction, etc."
    ::= { ieee8021AaVidIsidAsgnsEntry 4 }

ieee8021AaVidIsidAsgnsRowStatus OBJECT-TYPE
    SYNTAX         RowStatus
    MAX-ACCESS     read-write
    STATUS         current
    DESCRIPTION
        "This object allows entries to be created and deleted in the ieee8021AaVidIsidAsgnsTable."
    ::= { ieee8021AaVidIsidAsgnsEntry 5 }

-- ===============================================================
-- Auto attach port table support
-- ===============================================================

ieee8021AaPortTable OBJECT-TYPE
    SYNTAX      SEQUENCE OF Ieee8021AaPortEntry
    MAX-ACCESS  not-accessible
    STATUS      current
    DESCRIPTION
        "This table contains port-specific data for the auto attach application."
    ::= { ieee8021AaConfig 5 }

ieee8021AaPortEntry OBJECT-TYPE
    SYNTAX      Ieee8021AaPortEntry
    MAX-ACCESS  not-accessible
    STATUS      current
    DESCRIPTION
        "Port-specific data related to the auto attach application."
    INDEX { ieee8021AaPortIfIndex,
			ieee8021AaPortNetId }
    ::= { ieee8021AaPortTable 1 }

Ieee8021AaPortEntry ::= SEQUENCE {
    ieee8021AaPortIfIndex        Integer32,
	ieee8021AaPortNetId		 	 OCTET STRING,
    ieee8021AaPortEnable         INTEGER,
    ieee8021AaPortRowStatus      RowStatus }

ieee8021AaPortIfIndex OBJECT-TYPE
    SYNTAX         Integer32 (0..65535)
    MAX-ACCESS     not-accessible
    STATUS         current
    DESCRIPTION
        "IfIndex on the interface (port) identifier attribute."
    ::= { ieee8021AaPortEntry 1 }
	
ieee8021AaPortNetId OBJECT-TYPE
    SYNTAX         OCTET STRING (SIZE (0..12))
    MAX-ACCESS     read-only
    STATUS         current
    DESCRIPTION
        "Identifies an AAS port uniquely within the adminstrative
		domain. The object is the concatenation of the ieee8021AaSystemMAC and
		ieee8021AaPortIfIndex. The identified port can be simple, a LAG, or a DRNI."
    ::= { ieee8021AaPortEntry 2 }

ieee8021AaPortEnable OBJECT-TYPE
    SYNTAX         INTEGER {
                       enabled(1),
                       disabled(2)
                   }
    MAX-ACCESS     read-create
    STATUS         current
    DESCRIPTION
        "The current port auto attach protocol enable. Indicates 
	whether auto attach TLVs will be included in LLDPDUs generated on 
	the port (enabled) or not (disabled)."
    ::= { ieee8021AaPortEntry 3 }

ieee8021AaPortRowStatus OBJECT-TYPE
    SYNTAX         RowStatus
    MAX-ACCESS     read-create
    STATUS         current
    DESCRIPTION
        "This object allows entries to be created, deleted and modified in the
		ieee8021AaPortTable, if the operation is supported by the agent."
    ::= { ieee8021AaPortEntry 4 }

-- ===============================================================
-- Auto attach discovered systems table support
-- ===============================================================

ieee8021AaDiscSystemsTable OBJECT-TYPE
    SYNTAX      SEQUENCE OF Ieee8021AaDiscSystemsEntry
    MAX-ACCESS  not-accessible
    STATUS      current
    DESCRIPTION
        "This table contains details about locally connected AASs that have 
		been discovered."
    ::= { ieee8021AaConfig 6 }

ieee8021AaDiscSystemsEntry OBJECT-TYPE
    SYNTAX      Ieee8021AaDiscSystemsEntry
    MAX-ACCESS  not-accessible
    STATUS      current
    DESCRIPTION
        "Contains details about a locally connected AAS."
    INDEX { ieee8021AaDiscLocPortIfIndex,
			ieee8021AaDiscRemPortNetId }
    ::= { ieee8021AaDiscSystemsTable 1 }

Ieee8021AaDiscSystemsEntry ::= SEQUENCE {
    ieee8021AaDiscLocPortIfIndex       Integer32,
    ieee8021AaDiscRemSystemType        INTEGER,
    ieee8021AaDiscRemPortNetId         OCTET STRING,
    ieee8021AaDiscRemPortTagging       BITS,
    ieee8021AaDiscRemPortAssocState        INTEGER,
    ieee8021AaDiscLocPortAssocState        INTEGER }

ieee8021AaDiscLocPortIfIndex OBJECT-TYPE
    SYNTAX         Integer32 (0..65535)
    MAX-ACCESS     not-accessible
    STATUS         current
    DESCRIPTION
        "Identifies the interface through which the AAS 
	represented by this entry was discovered."
    ::= { ieee8021AaDiscSystemsEntry 1 }

ieee8021AaDiscRemSystemType OBJECT-TYPE
    SYNTAX         INTEGER {
                       aaBeb(1),
                       aaDeviceCVlanAware(2),
                       aaDeviceVlanUnaware(3),
					   aaDeviceSVlanAware(4),
                   }
    MAX-ACCESS     read-only
    STATUS         current
    DESCRIPTION
        "Identifies the AAS type as advertised through LLDP." 
    ::= { ieee8021AaDiscSystemsEntry 2 }

ieee8021AaDiscRemPortNetId OBJECT-TYPE
    SYNTAX         OCTET STRING (SIZE (0..12))
    MAX-ACCESS     read-only
    STATUS         current
    DESCRIPTION
        "Identifies an AAS port uniquely within the adminstrative
		domain. The object is the concatenation of the ieee8021AaSystemMAC and
		port IfIndex. The identified port can be simple, a LAG, or a DRNI."
    ::= { ieee8021AaDiscSystemsEntry 3 }

ieee8021AaDiscRemPortTagging OBJECT-TYPE
    SYNTAX         BITS {
                       trafficTagged(0),
                       trafficTaggedAndUntagged(1),
                       trafficUntaggedOnly(2)
                   }
    MAX-ACCESS     read-only
    STATUS         current
    DESCRIPTION
        "Exports the tagging data associated with the discovered Auto 
	Attach System as advertised through LLDP. When bit 0 is set to 0, 
	it means that all traffic is tagged the on link; when bit 0 is set 
	to 1, it means that the link supports both tagged and untagged traffic. 
	When bit 2 is set to 1 it means that the link supports only untagged traffic."
    ::= { ieee8021AaDiscSystemsEntry 4 }

ieee8021AaDiscRemPortAssocState OBJECT-TYPE
    SYNTAX         INTEGER {
                not_ready(0), -- initializing, not ready
				ready_to_assoc(1), -- ready to associate
                ready_to_attach(2), -- viable partner
		        assoc-fail_types(18), -- System type mismatched
				assoc-fail_tags(34), -- Tagging mismatched
				assoc-fail_topo(50), -- Multipoint link detected
				assoc_fail_other(66), -- Parsing or resourcing error
		        assoc_attached(3), -- port is active
                assoc_standby(19) -- at AAD, active elsewhere
				assoc_invalid(35) -- at AAB, AAD active elsewhere 
                   }
    MAX-ACCESS     read-only
    STATUS         current
    DESCRIPTION    
        "The current remote operational status for the associated interface."
    ::= { ieee8021AaDiscSystemsEntry 5 }

ieee8021AaDiscLocPortAssocState OBJECT-TYPE
    SYNTAX	    INTEGER {
                not_ready(0), -- initializing, not ready
				ready_to_assoc(1), -- advertising ready to associate
                ready_to_attach(2), -- viable partner
		        assoc-fail_types(18), -- System type mismatched
				assoc-fail_tags(34), -- Tagging mismatched
				assoc-fail_topo(50), -- Multipoint link detected
				assoc_fail_other(66), -- Parsing or resourcing error
		        assoc_attached(3), -- port is active
                assoc_standby(19) -- at AAD, active elsewhere
				assoc_invalid(35) -- at AAB, AAD active elsewhere
                   }
    MAX-ACCESS     read-only
    STATUS         current
    DESCRIPTION    
        "The current local operational status for the associated interface."
    ::= { ieee8021AaDiscSystemsEntry 6 }

-- ===============================================================
-- AAS statistics and error counters table
-- ===============================================================

ieee8021AaStatsTable  OBJECT-TYPE
    SYNTAX        SEQUENCE OF Ieee8021AaStatsEntry
    MAX-ACCESS    not-accessible
    STATUS        current
    DESCRIPTION   
        "This table contains auto attach port statistics data."
    ::= { ieee8021AaStats 1 }

ieee8021AaStatsEntry OBJECT-TYPE
    SYNTAX        Ieee8021AaStatsEntry
    MAX-ACCESS    not-accessible
    STATUS        current
    DESCRIPTION   
        "Each entry contains auto attach operational statistics for a 
	specific auto attach System port. Ports are identified by their MIB II 
	ifIndex value."
    INDEX         { ieee8021AaStatsPortIfIndex }
    ::= { ieee8021AaStatsTable 1 }

Ieee8021AaStatsEntry ::= SEQUENCE {
    ieee8021AaStatsPortIfIndex            Integer32,
    ieee8021AaStatsAssocAttached     	  Counter32,
	ieee8021AaStatsAssocFailed       	  Counter32,
	ieee8021AaStatsAssocReset			  Counter32,
	ieee8021AaStatsAssocStandby			  Counter32,
    ieee8021AaStatsAsgnsRequested         Counter32,
    ieee8021AaStatsAsgnsAccepted          Counter32,
    ieee8021AaStatsAsgnRejected           Counter32,
    ieee8021AaStatsAsgnsWithdrawn         Counter32 }

ieee8021AaStatsPortIfIndex OBJECT-TYPE
    SYNTAX        Integer32 (0..65535)
    MAX-ACCESS    not-accessible
    STATUS        current
    DESCRIPTION   
        "An index value that uniquely identifies a port. This value 
	corresponds to a MIB II ifIndex."
    ::= { ieee8021AaStatsEntry 1 }

ieee8021AaStatsAssocAttached OBJECT-TYPE
    SYNTAX        Counter32
    MAX-ACCESS    read-only
    STATUS        current
    DESCRIPTION   
        "Indicates the number of PBBN Auto Attach System TLVs received on the 
		identified port."
    ::= { ieee8021AaStatsEntry 2 }

ieee8021AaStatsAsgnsRequested OBJECT-TYPE
    SYNTAX        Counter32
    MAX-ACCESS    read-only
    STATUS        current
    DESCRIPTION   
        "Indicates the number of I-SID/VID bindings received in PBBN Auto Attach 
	Assignment TLVs on the identified port."
    ::= { ieee8021AaStatsEntry 3 }

ieee8021AaStatsAsgnsAccepted OBJECT-TYPE
    SYNTAX        Counter32
    MAX-ACCESS    read-only
    STATUS        current
    DESCRIPTION   
        "Indicates the number of I-SID/VID bindings from received PBBN Auto Attach 
	Assignment TLVs that are accepted (activated) on the 
	identified port. Counter is incremented when the binding transitions 
	from a non-accepted state (e.g., 'pending', 'rejected') to the 
	accepted state. The AAD counts the number received from the AAB while
	the AAB counts the number transmitted to the AAD."
    ::= { ieee8021AaStatsEntry 4 }

ieee8021AaStatsAsgnRejected OBJECT-TYPE
    SYNTAX        Counter32
    MAX-ACCESS    read-only
    STATUS        current
    DESCRIPTION   
        "Indicates the number of I-SID/VID bindings from received Auto Attach 
	Assignment TLVs that are rejected on the identified port. 
	Counter is incremented when the binding transitions from a non-rejected
	state (e.g., 'pending', 'accepted') to the rejected state.The AAD counts
	the number received from the AAB while the AAB counts the number
	transmitted to the AAD."
    ::= { ieee8021AaStatsEntry 5 }

ieee8021AaStatsAssocFailed OBJECT-TYPE
    SYNTAX        Counter32
    MAX-ACCESS    read-only
    STATUS        current
    DESCRIPTION   
        "Indicates the number of discovered AAS from received 
	AA System TLVs that have failed association or attachment due to errors
	such as system mismatches, multi-point link, incompatible tagging, etc." 
    ::= { ieee8021AaStatsEntry 6 }

ieee8021AaStatsAsgnsWithdrawn OBJECT-TYPE
    SYNTAX        Counter32
    MAX-ACCESS    read-only
    STATUS        current
    DESCRIPTION   
        "Indicates the number of I-SID/VID bindings from received PBBN Auto Attach 
	Assignment TLVs that have been deleted on the identified 
	port. Counter is only incremented when bindings are deleted for 
	reasons other than expiration." 
    ::= { ieee8021AaStatsEntry 7 }
	
ieee8021AaStatsAssocReset OBJECT-TYPE
    SYNTAX        Counter32
    MAX-ACCESS    read-only
    STATUS        current
    DESCRIPTION   
        "Indicates the number of discovered AAS from received 
	AA System TLVs that have reset an association or attachment due deleted
	discovered system tlvs, etc. This condition is most commonly a result of an
	AAS being reset or powered down." 
    ::= { ieee8021AaStatsEntry 8 }

ieee8021AaStatsAssocStandby OBJECT-TYPE
    SYNTAX        Counter32
    MAX-ACCESS    read-only
    STATUS        current
    DESCRIPTION   
        "Indicates the number of discovered AAS from received 
	AA System TLVs that have had an association in standby." 
    ::= { ieee8021AaStatsEntry 9 }	

-- ===============================================================
-- Auto attach notification objects
-- ===============================================================

ieee8021AaDiscSystemsDescr OBJECT-TYPE
    SYNTAX         SnmpAdminString (SIZE(0..255))
    MAX-ACCESS     accessible-for-notify
    STATUS         current
    DESCRIPTION    
        "The string value used to identify the LLDP system description of the 
	remote system distributed through LLDPDUs." 
    REFERENCE
        "IEEE 802.1AB-2016 8.5.7.2"
    ::= { ieee8021AaNotifyObjects 1 }

ieee8021AaDiscSystemsMgmtOid OBJECT-TYPE
    SYNTAX         OBJECT IDENTIFIER
    MAX-ACCESS     accessible-for-notify
    STATUS         current
    DESCRIPTION
        "The OID value used to identify the type of hardware component or 
	protocol entity associated with the management address advertised by 
	the remote system agent distributed through LLDP."
    REFERENCE
        "IEEE 802.1AB-2016 8.5.9.8"
    ::= { ieee8021AaNotifyObjects 2 }

-- ===============================================================
-- Auto attach notifications
-- ===============================================================

ieee8021AaDiscoveredSystem NOTIFICATION-TYPE
    OBJECTS        {
                       ieee8021AaDiscRemSystemType,
                       ieee8021AaDiscRemPortNetId,
                       ieee8021AaDiscSystemsDescr,  
                       ieee8021AaDiscSystemsMgmtOid 
                   }
    STATUS         current
    DESCRIPTION
        "This notification is generated when an AAS is discovered."
    ::= { ieee8021AaNotifications  1 }
	
	
-- =====================================================================
-- IEEE 802.1 - Auto attach conformance information
-- =====================================================================

ieee8021AaConformance OBJECT IDENTIFIER ::= { ieee8021PbbnAutoAttachMib 4 }

ieee8021AaCompliances 
    OBJECT IDENTIFIER ::= { ieee8021AaConformance 1 }
ieee8021AaGroups 
    OBJECT IDENTIFIER ::= { ieee8021AaConformance 2 }

	
-- 
-- Auto attach - compliance statements
-- 

ieee8021AaCompliance MODULE-COMPLIANCE
    STATUS        current
    DESCRIPTION
         "A compliance statement for SNMP entities that implement
         the IEEE 802.1Qcj auto attach MIB.

         This group is mandatory for agents that implement the 
         auto attach aaSet TLV set."
    MODULE        -- this module
        MANDATORY-GROUPS  { ieee8021AaGroup }
    ::= { ieee8021AaCompliances 1 }


--
-- Auto attach - MIB groupings
--

ieee8021AaGroup  OBJECT-GROUP
    OBJECTS {
		ieee8021AaSystemEnable,
		ieee8021AaSystemType,
		ieee8021AaSystemMAC,	
		ieee8021AaVidIsidAsgnsStatus,		
		ieee8021AaVidIsidAsgnsRowStatus,
		ieee8021AaPortNetId,
		ieee8021AaPortEnable,
		ieee8021AaDiscRemPortNetId,
		ieee8021AaStatsAssocAttached,
		ieee8021AaStatsAsgnsRequested,
		ieee8021AaStatsAsgnsAccepted,
		ieee8021AaStatsAsgnRejected,
		ieee8021AaDiscSystemsDescr,
		ieee8021AaDiscSystemsMgmtOid
      }
    STATUS  current
    DESCRIPTION
        "The collection of objects that support configuration of the PBBN
		auto attach service"
    ::= { ieee8021AaGroups 1 }

END
