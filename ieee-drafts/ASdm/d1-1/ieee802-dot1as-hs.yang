module ieee802-dot1as-hs {
  yang-version 1.1;
  namespace "urn:ieee:std:802.1AS:yang:ieee802-dot1as-hs";
  prefix dot1as-hs;

  import ieee1588-ptp {
    prefix ptp;
  }
  import ieee802-dot1as-ptp {
    prefix dot1as-ptp;
  }

  organization
    "IEEE 802.1 Working Group";
  contact
    "WG-URL: http://ieee802.org/1/
     WG-EMail: stds-802-1-l@ieee.org

     Contact: IEEE 802.1 Working Group Chair
              Postal: C/O IEEE 802.1 Working Group
              IEEE Standards Association
              445 Hoes Lane
              Piscataway, NJ 08854
              USA

     E-mail: stds-802-1-chairs@ieee.org";
  description
    "Management objects that control hot standby systems as specified in
     IEEE Std 802.1ASdm-d1.1.

     Copyright (C) IEEE (2023).
     This version of this YANG module is part of IEEE Std 802.1ASdm;
     see the standard itself for full legal notices.";

  revision 2023-07-14 {
    description
      "Published as part of IEEE Std 802.1ASdm-XXXX.
       fix for port-statistics-ds tree.";
    reference
      "IEEE Std 802.1ASdm-XXXX - YANG Data Model";
  }

  revision 2023-07-12 {
    description
      "Published as part of IEEE Std 802.1ASdm-XXXX.
       Initial version.";
    reference
      "IEEE Std 802.1ASdm-XXXX - YANG Data Model";
  }

  // The year (XXXX) will be replaced during publication.
  // This is the 1st balloted draft D0.1
  // of the YANG module for amendment IEEE P802.1ASdm.

  feature hot-standby {
    description
      "This feature indicates that the device supports the hot-standby functionality.";
  }

  typedef ptp-instance-state-type {
    type enumeration {
      enum not-capable {
        value 0;
        description
          "For all enabled PTP ports, asCapable is FALSE, i.e., the neighbor is not
               exchanging the messages that are required for conformance to this standard.";
      }
      enum synced {
        value 1;
        description
          "Time is synchronized to the requirements of this standard (see 17.5.3 and 17.5.4), or to
               the requirements specified by a profile standard.";
      }
      enum not-synced {
        value 2;
        description
          "On the PTP Port in SlavePort state, the port failed to receive time synchronization
               event messages or is not synchronized according to the requirements of this standard (see 17.5.3 and
               17.5.4), or to the requirements specified by a profile standard.";
      }
      enum initializing {
        value 3;
        description
          "Time synchronization does not conform to the requirements of this standard.";
      }
    }
  }

  typedef hot-standby-system-state-type {
    type enumeration {
      enum init {
        value 0;
        description
          "Initialization after the HotStandbySystem powers on and is enabled. In this state, the system is
           waiting for both PTP Instances to synchronize.";
      }
      enum redundant {
        value 1;
        description
          "Both PTP Instances are synchronized according to the requirements of the
           respective application or profile standard (see 3.24). Time synchronization is redundant.";
      }
      enum not-redundant {
        value 2;
        description
          "One PTP Instance is synchronized, and the other PTP Instance is faulted (not
           synchronized). Time synchronization continues to meet the requirements of the respective
           application or profile standard (see 3.24). Time synchronization is not redundant.";
      }
      enum out-of-sync {
        value 3;
        description
          "The HotStandbySystem is adjusting phase/frequency of its local time using the
           data stored while the system was in the REDUNDANT or NOT_REDUNDANT state, but the local
           time will eventually drift relative to other time-aware systems. During OUT_OF_SYNC state, time
           synchronization might not meet the requirements of the respective application or profile standard
           (see 3.24).";
      }
    }
  }

  augment "/ptp:ptp/ptp:instances/ptp:instance" {
    description
      "Augment IEEE Std 1588 instanceList.";
    container ptp-instance-sync-ds {
      description
        "The ptpInstanceSyncDS describes the synchronization status of the PTP Instance.";
      reference
        "14.8 of IEEE Std 802.1ASdm-2023";
      leaf ptp-instance-state {
        type ptp-instance-state-type;
        config false;
        description
          " State of the PTP Instance with respect to requirements of the respective
           application or profile standard";
        reference
          "14.8.2 of IEEE Std 802.1ASdm-2023";
      }
      leaf offset-from-master-threshold {
        type ptp:time-interval;
        config true;
        description
          "The value is the threshold for offsetFromMaster (see 17.5.1.2), below which the PTP Instance is considered
           to be synchronized.";
        reference
          "14.8.3";
      }
      leaf rx_slave-port-sync-count-threshold {
        type uint32;
        config true;
        description
          "The value of rxSlavePortSyncCountThreshold is the threshold for rxSyncCountSlaveP (see 17.5.1.4), above
           which the PTP Instance is considered to be synchronized.";
        reference
          "14.8.4";
      }
      leaf thresh-exceedance {
        type uint32;
        config true;
        description
          "The value of threshExceedance (see 17.5.1.7) is the threshold for the number of consecutive exceedances of
           offsetFromMasterThreshold (see 17.5.1.3) by offsetFromMaster (see 17.5.1.2), at which the PTP Instance is
           no longer in the SYNCED state (see 17.5.3.3).";
        reference
          "14.8.5";
      }
      leaf thresh-in-ranges {
        type uint32;
        config true;
        description
          "The value of threshInRanges (17.5.1.9) is the threshold for the number of consecutive occurrences of
           offsetFromMaster (see 17.5.1.2) being within offsetFromMasterThreshold (see 17.5.1.3), at which the PTP
           Instance is placed in the SYNCED state (see 17.5.3.3).";
        reference
          "14.8.6";
      }
    }
    container drift-tracking-ds {
      description
        "The driftTrackingDS contains a managed object that is used to enable or disable the optional Drift_Tracking
         TLV.";
      reference
        "14.9 of IEEE Std 802.1ASdm-2023";
      leaf drift-tracking-tlv-support {
        type boolean;
        config true;
        description
          "The value of driftTrackingTlvSupport indicates whether the Drift_Tracking TLV is enabled or disabled.";
        reference
          "14.9.2 of IEEE Std 802.1ASdm-2023";
      }
    }
  }

  augment "/ptp:ptp/ptp:instances/ptp:instance/ptp:ports/ptp:port/ptp:port-ds" {
    description
      "Augment IEEE Std 1588 cmommonServices.";
    leaf gptp-capable-state-machines-enabled {
      type boolean;
      config true;
      description
        "A Boolean that is used to enable or disable the GptpCapableTransmit, GptpCapableReceive, and
         GptpCapableIntervalSetting state machines.";
      reference
        "14.8.55 of IEEE Std 802.1ASdm-2023";
    }
  }

  augment "/ptp:ptp/ptp:instances/ptp:instance/ptp:ports/ptp:port/dot1as-ptp:port-statistics-ds" {
    description
      "Augment IEEE Std 802.1AS PortStatisticsDS.";
    leaf rx-sync-count-slave-p {
      type uint32;
      config false;
      description
        "This counter increments whenever time synchronization information is received on a PTP Port
         when its port state is SlavePort.";
      reference
        "14.10.20 of IEEE Std 802.1ASdm-2023";
    }
  }

  augment "/ptp:ptp/ptp:common-services" {
    description
      "Augment IEEE Std 1588 cmommonServices.

       14.6.9 of IEEE Std 802.1AS-2020 specifies neighborRateRatio
       (neighbor-rate-ratio), which is provided in YANG as the
       semantically equivalent node in ieee1588-ptp named
       scaled-neighbor-rate-ratio (in link-port-ds).";
    container hot-standby-system {
      if-feature "hot-standby";
      description
        "The hotStandbyService structure contains the hotStandbySystemList, which is a list of instances of the Hot
         Standby Service.";
      reference
        "14.1.1 of IEEE Std 802.1ASdm-2023";
      list hot-standby-sytem {
        description
          "List of instances of the Hot Standby Service";
        reference
          "14.1.1 of IEEE Std 802.1ASdm-2023";
        key "hot-standby-system-index";
        leaf hot-standby-system-index {
          type uint8;
          config true;
        }
        container hot-standby-system-ds {
          description
            "The hotStandbySystemDS describes the attributes of the respective instance of the Hot Standby Service.";
          reference
            "14.19 of IEEE Std 802.1ASdm-2023";
          leaf primary-ptp-instance-index {
            type uint32;
            config true;
            description
              "The value of primaryPtpInstanceIndex is the index (see 14.1.1) of the primary PTP Instance associated with
               this hotStandbySystem instance.";
            reference
              "14.19.2 of IEEE Std 802.1ASdm-2023";
          }
          leaf secondary-ptp-instance-index {
            type uint32;
            config true;
            description
              "The value of secondaryPtpInstanceIndex is the index (see 14.1.1) of the secondaryPTP Instance associated
               with this hotStandbySystem instance.";
            reference
              "14.19.3 of IEEE Std 802.1ASdm-2023";
          }
          leaf hot-standby-system-enable {
            type boolean;
            config true;
            description
              "The value is the hotStandbySystemEnable attribute of the HotStandbySystem entity (see 17.6.1.2).";
            reference
              "14.19.4 of IEEE Std 802.1ASdm-2023";
          }
          leaf hot-standby-system-state {
            type hot-standby-system-state-type;
            config false;
            description
              "The value of hotStandbySystemState is the state of the hotStandbySystem, i.e., the value of the global
               variable hotStandbySystemState (see 17.6.1.1).";
            reference
              "14.19.5 of IEEE Std 802.1ASdm-2023";
          }
          leaf hot-standby-system-log-sync-time-threshold {
            type int8;
            config true;
            description
              "The value of hotStandbySystemLogSyncTimeThreshold1 is the logarithm to base 2 of the time interval, in
               seconds, after which a hotStandbySystem in the INIT state transitions from the INIT state to the
               NOT_REDUNDANT state if the conditions to transition to the REDUNDANT state are not met (see
               17.6.4). The value -128 means that the transition time is zero, i.e., the transition occurs immediately.";
            reference
              "14.19.6 of IEEE Std 802.1ASdm-2023";
          }
          leaf hot-standby-system-split-functionality {
            type boolean;
            config true;
            description
              "If the value is TRUE, the optional split functionality (see 17.6.3.4) is used. If the value is FALSE, the
               optional split functionality is not used.";
            reference
              "14.19.8 of IEEE Std 802.1ASdm-2023";
          }
          leaf primary-secondary-offset {
            type dot1as-ptp:scaled-ns;
            config false;
            description
              "The absolute value of the difference between the clockSlaveTimes (see 10.2.4.3) of the primary and
               secondary PTP Instances.";
            reference
              "14.19.9 of IEEE Std 802.1ASdm-2023";
          }
          leaf primary-secondary-offset-threshold {
            type dot1as-ptp:scaled-ns;
            config true;
            description
              "The threshold for hotStandbySystemDS.primarySecondaryOffset (see 14.19.9), above which the
               hotStandbySytemState transitions from REDUNDANT to NOT_REDUNDANT, or does not transition from
               NOT_REDUNDANT or OUT_OF_SYNC to REDUNDANT even if other conditions for these transitions
               are satisfied.";
            reference
              "14.19.10 of IEEE Std 802.1ASdm-2023";
          }
        }
        container hot-standby-system-description-ds {
          description
            "The hotStandbySystemDescriptionDS contains descriptive information for the respective instance of the Hot Standby Service.";
          reference
            "14.20 of IEEE Std 802.1ASdm-2023";
          leaf user-description {
            type string {
              length "0..128";
            }
            config true;
            description
              "Configurable description of the hot standby system.";
            reference
              "14.20.3 of IEEE Std 802.1ASdm-2023";
          }
        }
      }
    }
  }
}
